--------------------------------------------------
--Version Number: 20070410001
--------------------------------------------------

ES3626A-MIB DEFINITIONS ::= BEGIN

IMPORTS
        MODULE-IDENTITY, OBJECT-TYPE, Unsigned32, Integer32, Counter32, IpAddress,
        NOTIFICATION-TYPE, enterprises, Gauge32, TimeTicks, Counter64
                FROM SNMPv2-SMI
        DisplayString, RowStatus, MacAddress, TruthValue, TEXTUAL-CONVENTION, DateAndTime, RowPointer
                FROM SNMPv2-TC
        PortList, VlanIndex
                FROM Q-BRIDGE-MIB
        SnmpAdminString
                FROM SNMP-FRAMEWORK-MIB
        EnabledStatus
                FROM P-BRIDGE-MIB
        BridgeId, Timeout, dot1dStpPort
                FROM BRIDGE-MIB
        vrrpOperVrId
                FROM VRRP-MIB
        ZeroBasedCounter64
                FROM HCNUM-TC
        InterfaceIndex, ifIndex, InterfaceIndexOrZero
                FROM IF-MIB
        diffServClfrEntry, diffServMultiFieldClfrEntry, IndexIntegerNextFree, IndexInteger
                FROM DIFFSERV-MIB
        ipNetToMediaEntry
                FROM IP-MIB
        InetAddressType, InetAddress, InetAddressPrefixLength, InetPortNumber
                FROM INET-ADDRESS-MIB
        dot1xAuthConfigEntry
                FROM IEEE8021-PAE-MIB;


accton              OBJECT IDENTIFIER ::= { enterprises 259 }
snmpMgt             OBJECT IDENTIFIER ::= { accton 6 }
cheetahSwitchMgt    OBJECT IDENTIFIER ::= { snmpMgt 10 }


es3626aMIB MODULE-IDENTITY
        LAST-UPDATED "200703300000Z"
        ORGANIZATION "Accton Technology Corp."
        CONTACT-INFO
                "Accton Technology Corp.
                 Customer Service

                 Postal: No. 1 Creation Rd. III,
                         Science-based Industrial Park,
                         Hsinchu 300-77, Taiwan, R.O.C.

                 Tel: +886-3-5770270

                 E-mail: support@accton.com.tw"
        DESCRIPTION
                "The MIB module for ES3626A."
        REVISION "200109060000Z"
        DESCRIPTION
                "Initial version of this MIB."
        ::= { cheetahSwitchMgt 999 }


es3626aMIBObjects          OBJECT IDENTIFIER ::= { es3626aMIB 1 }
es3626aMIBNotifications    OBJECT IDENTIFIER ::= { es3626aMIB 2 }
es3626aMIBConformance      OBJECT IDENTIFIER ::= { es3626aMIB 3 }


switchMgt           OBJECT IDENTIFIER ::= { es3626aMIBObjects 1 }
portMgt             OBJECT IDENTIFIER ::= { es3626aMIBObjects 2 }
trunkMgt            OBJECT IDENTIFIER ::= { es3626aMIBObjects 3 }
lacpMgt             OBJECT IDENTIFIER ::= { es3626aMIBObjects 4 }
staMgt              OBJECT IDENTIFIER ::= { es3626aMIBObjects 5 }
tftpMgt             OBJECT IDENTIFIER ::= { es3626aMIBObjects 6 }
restartMgt          OBJECT IDENTIFIER ::= { es3626aMIBObjects 7 }
mirrorMgt           OBJECT IDENTIFIER ::= { es3626aMIBObjects 8 }
igmpSnoopMgt        OBJECT IDENTIFIER ::= { es3626aMIBObjects 9 }
ipMgt               OBJECT IDENTIFIER ::= { es3626aMIBObjects 10 }
bcastStormMgt       OBJECT IDENTIFIER ::= { es3626aMIBObjects 11 }
vlanMgt             OBJECT IDENTIFIER ::= { es3626aMIBObjects 12 }
priorityMgt         OBJECT IDENTIFIER ::= { es3626aMIBObjects 13 }
trapDestMgt         OBJECT IDENTIFIER ::= { es3626aMIBObjects 14 }
vdslMgt             OBJECT IDENTIFIER ::= { es3626aMIBObjects 15 }
qosMgt              OBJECT IDENTIFIER ::= { es3626aMIBObjects 16 }
securityMgt         OBJECT IDENTIFIER ::= { es3626aMIBObjects 17 }
layer3Mgt           OBJECT IDENTIFIER ::= { es3626aMIBObjects 18 }
sysLogMgt           OBJECT IDENTIFIER ::= { es3626aMIBObjects 19 }
lineMgt             OBJECT IDENTIFIER ::= { es3626aMIBObjects 20 }
bladeMgt            OBJECT IDENTIFIER ::= { es3626aMIBObjects 21 }
ftthMgt             OBJECT IDENTIFIER ::= { es3626aMIBObjects 22 }
sysTimeMgt          OBJECT IDENTIFIER ::= { es3626aMIBObjects 23 }
fileMgt             OBJECT IDENTIFIER ::= { es3626aMIBObjects 24 }
vrrpMgt             OBJECT IDENTIFIER ::= { es3626aMIBObjects 25 }
dnsMgt              OBJECT IDENTIFIER ::= { es3626aMIBObjects 26 }
ledCtrlMgt          OBJECT IDENTIFIER ::= { es3626aMIBObjects 27 }
poeMgt              OBJECT IDENTIFIER ::= { es3626aMIBObjects 28 }
hsrpMgt             OBJECT IDENTIFIER ::= { es3626aMIBObjects 29 }
diffServMgtOld      OBJECT IDENTIFIER ::= { es3626aMIBObjects 30 } -- Duplicate definition diffServMgt, so temp rename to diffServMgtOld
dot1dTpMgt          OBJECT IDENTIFIER ::= { es3626aMIBObjects 31 }
amapMgt             OBJECT IDENTIFIER ::= { es3626aMIBObjects 32 }
stormMgt            OBJECT IDENTIFIER ::= { es3626aMIBObjects 33 }
radiusAuthClientMgt             OBJECT IDENTIFIER ::= { es3626aMIBObjects 34 }
configurationChangeMgt          OBJECT IDENTIFIER ::= { es3626aMIBObjects 35 }
configurationManagementMgt      OBJECT IDENTIFIER ::= { es3626aMIBObjects 36 }
mstpMgt                         OBJECT IDENTIFIER ::= { es3626aMIBObjects 37 }
aliasMgt                        OBJECT IDENTIFIER ::= { es3626aMIBObjects 38 }
sysResourceMgt                  OBJECT IDENTIFIER ::= { es3626aMIBObjects 39 }
alertLedMgt                     OBJECT IDENTIFIER ::= { es3626aMIBObjects 40 }
ietfBridgeMibExtMgt             OBJECT IDENTIFIER ::= { es3626aMIBObjects 41 }
vlanAuthorizationMgt            OBJECT IDENTIFIER ::= { es3626aMIBObjects 42 }
sbcMgt                          OBJECT IDENTIFIER ::= { es3626aMIBObjects 43 }
mvrMgt                          OBJECT IDENTIFIER ::= { es3626aMIBObjects 44 }
egressPacketBlockMgt            OBJECT IDENTIFIER ::= { es3626aMIBObjects 45 }
dhcpSnoopMgt                    OBJECT IDENTIFIER ::= { es3626aMIBObjects 46 }
clusterMgt                      OBJECT IDENTIFIER ::= { es3626aMIBObjects 47 }
ipSrcGuardMgt                   OBJECT IDENTIFIER ::= { es3626aMIBObjects 48 }
upnpMgt             OBJECT IDENTIFIER ::= { es3528moMIBObjects 49 }


-- -------------------------------------------------------------
-- Textual Conventions
-- -------------------------------------------------------------

--  The Area ID, in OSPF, has the same format as an IP Address,
--  but has the function of defining a summarization point for
--  Link State Advertisements

OspfAreaID ::= TEXTUAL-CONVENTION
    STATUS      current
    DESCRIPTION
       "An OSPF Area Identifier."
    SYNTAX      IpAddress

--  The OSPF Metric is defined as an unsigned value in the range

OspfBigMetric ::= TEXTUAL-CONVENTION
    STATUS      current
    DESCRIPTION
       "The OSPF External Metric."
    SYNTAX      Integer32 (0..'FFFFFE'h)

--sshv2 only start
KeySegment ::= TEXTUAL-CONVENTION
    STATUS      current
    DESCRIPTION
        "The total length of the key is 1024 characters,
         it is divided into 8 parts and stored in 8 separated mib
         variables as below:

             Key1: part 1 of the key (1-128)
             Key2: part 2 of the key (129-256)
             Key3: part 3 of the key (257-384)
             Key4: part 4 of the key (385-512)
             Key5: part 5 of the key (513-640)
             Key6: part 6 of the key (641-768)
             Key7: part 7 of the key (769-896)
             Key8: part 8 of the key (897-1024)

         Please note that if the key string is less then 1024 characters,
         the remaining part of the string will be filled by a zero-length string.
         For example, if the length of the key is 129,
         we will get a string of length 128 in Key1, and
         a string of length 1 in Key2,
         moreover, Key3 to Key8 will all be zero-length strings."
    SYNTAX      DisplayString(SIZE(0..128))
--sshv2 only end

ValidStatus ::= TEXTUAL-CONVENTION
    STATUS      current
    DESCRIPTION
        "A simple status value for the object to create and destroy
         a table entry. This is a simplified variant of RowStatus as it
         supports only two values. Setting it to valid(1) creates an entry.
         Setting it to invalid(2) destroys an entry."
    SYNTAX      INTEGER { valid(1), invalid(2) }

--for hsrpMgt start
HsrpState ::= TEXTUAL-CONVENTION
    STATUS current
    DESCRIPTION
            "The current state of the HSRP protocol for a given
             HSRP group entry."
    SYNTAX INTEGER {
        initial(1),
        learn(2),
        listen(3),
        speak(4),
        standby(5),
        active(6)
        }
--for hsrpMgt end

--for vdslLineMgt start

    VdslLineCodingType ::= TEXTUAL-CONVENTION
        STATUS       current
        DESCRIPTION
            "This data type is used as the syntax for the VDSL Line
            Code.  Attributes with this syntax identify the line coding
            used.  Specified as an INTEGER, the three values are:
            other(1)  -- none of the following
            mcm(2)    -- Multiple Carrier Modulation
            scm(3)    -- Single Carrier Modulation"
        SYNTAX  INTEGER
            {
            other(1),
            mcm(2),
            scm(3)
            }

    VdslLineEntity ::= TEXTUAL-CONVENTION
        STATUS       current
        DESCRIPTION
            "Identifies a transceiver as being either Vtuc or Vtur.
            A VDSL line consists of two transceivers, a Vtuc and a
            Vtur.  Attributes with this syntax reference the two sides
            of a line.  Specified as an INTEGER, the two values are:

            vtuc(1)  -- central site transceiver
            vtur(2)  -- remote site transceiver"
        SYNTAX  INTEGER
            {
            vtuc(1),
            vtur(2)
            }


--TEXTUAL-CONVENTION defined in HcPerfHistTC_Draft.mib start

    HCPerfValidIntervals ::= TEXTUAL-CONVENTION
        STATUS  current
        DESCRIPTION
           "The number of near-end intervals for which data was
           collected.  The value of an object with an
           HCPerfValidIntervals syntax will be 96 unless the
           measurement was (re-)started within the last 1440 minutes,
           in which case the value will be the number of complete 15
           minute intervals for which the agent has at least some data.
           In certain cases (e.g., in the case where the agent is a
           proxy) it is possible that some intervals are unavailable.
           In this case, this interval is the maximum interval number
           for which data is available."
        SYNTAX   Gauge32 (0..96)

    HCPerfInvalidIntervals ::= TEXTUAL-CONVENTION
        STATUS  current
        DESCRIPTION
           "The number of near-end intervals for which no data is
           available.  The value of an object with an
           HCPerfInvalidIntervals syntax will typically be zero except
           in cases where the data for some intervals are not available
           (e.g., in proxy situations)."
        SYNTAX   Gauge32 (0..96)

    HCPerfTimeElapsed ::= TEXTUAL-CONVENTION
        STATUS  current
        DESCRIPTION
           "The number of seconds that have elapsed since the beginning
           of the current measurement period.  If, for some reason,
           such as an adjustment in the system's time-of-day clock or
           the addition of a leap second, the duration of the current
           interval exceeds the maximum value, the agent will return
           the maximum value.

           For 15 minute intervals, the range is limited to (0..899).
           For 24 hour intervals, the range is limited to (0..86399)."
        SYNTAX   Gauge32 (0..86399)

    HCPerfIntervalThreshold ::= TEXTUAL-CONVENTION
        STATUS   current
        DESCRIPTION
            "This convention defines a range of values that may be set
            to a fault threshold alarm control.  As the number of
            seconds in a 15-minute interval numbers at most 900,
            objects of this type may have a range of 0...900, where the
            value of 0 disables the alarm."
        SYNTAX   Unsigned32 (0..900)

    HCPerfCurrentCount ::= TEXTUAL-CONVENTION
        STATUS  current
        DESCRIPTION
            "A gauge associated with a performance measurement in a
             current 15 minute measurement interval.  The value of an
             object with an HCPerfCurrentCount syntax starts from zero
             and is increased when associated events occur, until the
             end of the 15 minute interval.  At that time the value of
             the gauge is stored in the first 15 minute history
             interval, and the gauge is restarted at zero.  In the case
             where the agent has no valid data available for the
             current interval, the corresponding object instance is not
             available and upon a retrieval request a corresponding
             error message shall be returned to indicate that this
             instance does not exist.

             This count represents a non-negative integer, which
             may increase or decrease, but shall never exceed 2^64-1
             (18446744073709551615 decimal), nor fall below 0.  The
             The value of an object with HCPerfCurrentCount syntax
             assumes its maximum value whenever the underlying count
             exceeds 2^64-1.  If the underlying count subsequently
             decreases below 2^64-1 (due, e.g., to a retroactive
             adjustment as a result of entering or exiting unavailable
             time), then the object's value also decreases.

             Note that this TC is not strictly supported in SMIv2,
             because the 'always increasing' and 'counter wrap'
             semantics associated with the Counter64 base type are not
             preserved.  It is possible that management applications
             which rely solely upon the (Counter64) ASN.1 tag to
             determine object semantics will mistakenly operate upon
             objects of this type as they would for Counter64 objects.

             This textual convention represents a limited and short-
             term solution, and may be deprecated as a long term
             solution is defined and deployed to replace it."
        SYNTAX  Counter64

    HCPerfIntervalCount ::= TEXTUAL-CONVENTION
        STATUS  current
        DESCRIPTION
            "A gauge associated with a performance measurement in
             a previous 15 minute measurement interval.  In the case
             where the agent has no valid data available for a
             particular interval, the corresponding object instance is
             not available and upon a retrieval request a corresponding
             error message shall be returned to indicate that this
             instance does not exist.

             Let X be an object with HCPerfIntervalCount syntax.
             Let Y be an object with HCPerfCurrentCount syntax.
             Let Z be an object with HCPerfTotalCount syntax.
             Then, In a system supporting a history of n intervals with
             X(1) and X(n) the most and least recent intervals
             respectively, the following applies at the end of a 15
             minute interval:

                - discard the value of X(n)
                - the value of X(i) becomes that of X(i-1)
                  for n >= i > 1
                - the value of X(1) becomes that of Y.
                - the value of Z, if supported, is adjusted.

             This count represents a non-negative integer, which
             may increase or decrease, but shall never exceed 2^64-1
             (18446744073709551615 decimal), nor fall below 0.  The
             The value of an object with HCPerfIntervalCount syntax
             assumes its maximum value whenever the underlying count
             exceeds 2^64-1.  If the underlying count subsequently
             decreases below 2^64-1 (due, e.g., to a retroactive
             adjustment as a result of entering or exiting unavailable
             time), then the value of the object also decreases.

             Note that this TC is not strictly supported in SMIv2,
             because the 'always increasing' and 'counter wrap'
             semantics associated with the Counter64 base type are not
             preserved.  It is possible that management applications
             which rely solely upon the (Counter64) ASN.1 tag to
             determine object semantics will mistakenly operate upon
             objects of this type as they would for Counter64 objects.

             This textual convention represents a limited and short-
             term solution, and may be deprecated as a long term
             solution is defined and deployed to replace it."
        SYNTAX  Counter64

    HCPerfTotalCount ::= TEXTUAL-CONVENTION
        STATUS  current
        DESCRIPTION
            "A gauge representing the aggregate of previous valid 15
             minute measurement intervals.  Intervals for which no
             valid data was available are not counted.

             This count represents a non-negative integer, which
             may increase or decrease, but shall never exceed 2^64-1
             (18446744073709551615 decimal), nor fall below 0.  The
             The value of an object with HCPerfTotalCount syntax
             assumes its maximum value whenever the underlying count
             exceeds 2^64-1.  If the underlying count subsequently
             decreases below 2^64-1 (due, e.g., to a retroactive
             adjustment as a result of entering or exiting unavailable
             time), then the object's value also decreases.

             Note that this TC is not strictly supported in SMIv2,
             because the 'always increasing' and 'counter wrap'
             semantics associated with the Counter64 base type are not
             preserved.  It is possible that management applications
             which rely solely upon the (Counter64) ASN.1 tag to
             determine object semantics will mistakenly operate upon
             objects of this type as they would for Counter64 objects.
             This textual convention represents a limited and short-
             term solution, and may be deprecated as a long term
             solution is defined and deployed to replace it."
        SYNTAX  Counter64

--TEXTUAL-CONVENTION defined in HcPerfHistTC_Draft.mib end
--for vdslLineMgt end

StaPathCostMode ::= TEXTUAL-CONVENTION
     STATUS  current
     DESCRIPTION
         "The path cost mode of a spanning tree algorithm, short(1) indicates
          that we retrieve/configure the spanning tree path cost as a 16 bit
          value and long(2) indicates that we retrieve/configure the spanning
          tree path cost as a 32 bit value."
     SYNTAX      INTEGER { short(1), long(2) }

-- for authMgt start
AuthMethodType ::= TEXTUAL-CONVENTION
       STATUS       current
       DESCRIPTION
               "The authentication method types."
       SYNTAX  INTEGER {
                   none(0),
                   local(1),
                   radius(2),
                   tacas(4)
               }
-- for authMgt end

FileCopyStatus ::= TEXTUAL-CONVENTION
       STATUS       current
       DESCRIPTION
               "The file copy result status."
       SYNTAX  INTEGER {
                    fileCopyTftpUndefError(1),
                    fileCopyTftpFileNotFound(2),
                    fileCopyTftpAccessViolation(3),
                    fileCopyTftpDiskFull(4),
                    fileCopyTftpIllegalOperation(5),
                    fileCopyTftpUnkownTransferId(6),
                    fileCopyTftpFileExisted(7),
                    fileCopyTftpNoSuchUser(8),
                    fileCopyTftpTimeout(9),
                    fileCopyTftpSendError(10),
                    fileCopyTftpReceiverError(11),
                    fileCopyTftpSocketOpenError(12),
                    fileCopyTftpSocketBindError(13),
                    fileCopyTftpUserCancel(14),
                    fileCopyTftpCompleted(15),
                    fileCopyParaError(16),
                    fileCopyBusy(17),
                    fileCopyUnknown(18),
                    fileCopyReadFileError(19),
                    fileCopySetStartupError(20),
                    fileCopyFileSizeExceed(21),
                    fileCopyMagicWordError(22),
                    fileCopyImageTypeError(23),
                    fileCopyHeaderChecksumError(24),
                    fileCopyImageChecksumError(25),
                    fileCopyWriteFlashFinish(26),
                    fileCopyWriteFlashError(27),
                    fileCopyWriteFlashProgramming(28),
                    fileCopyError(29),
                    fileCopySuccess(30),
                    fileCopyCompleted(31)
               }

--
-- switchMgt
--

-- Management for the switch system, or individual units
-- in a stackable switch system. For a non-stackable system,
-- only unit 1 exists.


switchManagementVlan OBJECT-TYPE
        SYNTAX      Integer32 (1..4094)
        MAX-ACCESS  read-write
        STATUS      current
        DESCRIPTION "The VLAN on which management is done."
        ::= { switchMgt 1 }

switchNumber OBJECT-TYPE
        SYNTAX      Integer32
        MAX-ACCESS  read-only
        STATUS      current
        DESCRIPTION "The total number of switches present on this system."
        ::= { switchMgt 2 }

switchInfoTable OBJECT-TYPE
        SYNTAX      SEQUENCE OF SwitchInfoEntry
        MAX-ACCESS  not-accessible
        STATUS      current
        DESCRIPTION "Table of descriptive and status information about
                     the switch units in this system."
        ::= { switchMgt 3 }

switchInfoEntry OBJECT-TYPE
        SYNTAX      SwitchInfoEntry
        MAX-ACCESS  not-accessible
        STATUS      current
        DESCRIPTION "Table providing descriptions and status information for
                     switch units."
        INDEX       { swUnitIndex }
        ::= { switchInfoTable 1 }

SwitchInfoEntry ::= SEQUENCE
{
    swUnitIndex             Integer32,
    swHardwareVer           DisplayString,
    swMicrocodeVer          DisplayString,
    swLoaderVer             DisplayString,
    swBootRomVer            DisplayString,
    swOpCodeVer             DisplayString,
    swPortNumber            Integer32,
    swPowerStatus           INTEGER,
    swRoleInSystem          INTEGER,
    swSerialNumber          DisplayString,
    swExpansionSlot1        INTEGER,
    swExpansionSlot2        INTEGER,
    swServiceTag            DisplayString,
    swModelNumber           DisplayString,
    swEpldVer               DisplayString,
    swExpectedModuleOpCodeVer DisplayString
}

swUnitIndex OBJECT-TYPE
        SYNTAX      Integer32
        MAX-ACCESS  not-accessible
        STATUS      current
        DESCRIPTION "This object identifies the switch within the system
                     for which this entry contains information. This
                     value can never be greater than switchNumber."
        ::= { switchInfoEntry 1 }

swHardwareVer OBJECT-TYPE
        SYNTAX      DisplayString (SIZE(0..20))
        MAX-ACCESS  read-only
        STATUS      current
        DESCRIPTION "Hardware version of the main board."
        ::= { switchInfoEntry 2 }

swMicrocodeVer OBJECT-TYPE
        SYNTAX      DisplayString (SIZE(0..20))
        MAX-ACCESS  read-only
        STATUS      current
        DESCRIPTION "Microcode version of the main board."
        ::= { switchInfoEntry 3 }

swLoaderVer OBJECT-TYPE
        SYNTAX      DisplayString (SIZE(0..20))
        MAX-ACCESS  read-only
        STATUS      current
        DESCRIPTION "Loader version of the main board."
        ::= { switchInfoEntry 4 }

swBootRomVer OBJECT-TYPE
        SYNTAX      DisplayString (SIZE(0..20))
        MAX-ACCESS  read-only
        STATUS      current
        DESCRIPTION "Boot ROM code version of the main board."
        ::= { switchInfoEntry 5 }

swOpCodeVer OBJECT-TYPE
        SYNTAX      DisplayString (SIZE(0..20))
        MAX-ACCESS  read-only
        STATUS      current
        DESCRIPTION "Operation code version of the main board."
        ::= { switchInfoEntry 6 }

swPortNumber OBJECT-TYPE
        SYNTAX      Integer32
        MAX-ACCESS  read-only
        STATUS      current
        DESCRIPTION "The number of ports on this switch."
        ::= { switchInfoEntry 7 }

swPowerStatus OBJECT-TYPE
        SYNTAX      INTEGER
                    {
                        internalPower(1),
                        redundantPower(2),
                        internalAndRedundantPower(3)
                    }
        MAX-ACCESS  read-only
        STATUS      current
        DESCRIPTION "Indicates the switch using internalPower(1),
                     redundantPower(2) or both(3)"
        ::= { switchInfoEntry 8 }

swRoleInSystem OBJECT-TYPE
        SYNTAX      INTEGER
                    {
                        master(1),
                        backupMaster(2),
                        slave(3)
                    }
        MAX-ACCESS  read-only
        STATUS      current
        DESCRIPTION "Indicates the switch is master(1), backupMaster(2)
                     or slave(3) in this system."
        ::= { switchInfoEntry 9 }

swSerialNumber OBJECT-TYPE
        SYNTAX      DisplayString (SIZE(0..80))
        MAX-ACCESS  read-only
        STATUS      current
        DESCRIPTION "Serial number of the switch."
        ::= { switchInfoEntry 10 }

swExpansionSlot1 OBJECT-TYPE
        SYNTAX      INTEGER
                    {
                        notPresent(1),
                        other(2),
                        hundredBaseFxScMmf(3),
                        hundredBaseFxScSmf(4),
                        hundredBaseFxMtrjMmf(5),
                        thousandBaseSxScMmf(6),
                        thousandBaseSxMtrjMmf(7),
                        thousandBaseXGbic(8),
                        thousandBaseLxScSmf(9),
                        thousandBaseT(10),
                        stackingModule(11),
                        thousandBaseSfp(12),
                        tenHundredBaseT4port(13),
                        tenHundredBaseFxMtrj4port(14),
                        comboStackingSfp(15),
                        tenHundredBaseT(16),
                        comboThousandBaseTxSfp(17),
                        eightPortSfpModule(18),
                        tenGigaPortModule(19),
                        hundredBaseScMcIfClassA(20),
                        hundredBaseScMcIfClassB(21)
                    }
        MAX-ACCESS  read-only
        STATUS      current
        DESCRIPTION "Type of expansion module in this switch slot 1."
        ::= { switchInfoEntry 11 }

swExpansionSlot2 OBJECT-TYPE
        SYNTAX      INTEGER
                    {
                        notPresent(1),
                        other(2),
                        hundredBaseFxScMmf(3),
                        hundredBaseFxScSmf(4),
                        hundredBaseFxMtrjMmf(5),
                        thousandBaseSxScMmf(6),
                        thousandBaseSxMtrjMmf(7),
                        thousandBaseXGbic(8),
                        thousandBaseLxScSmf(9),
                        thousandBaseT(10),
                        stackingModule(11),
                        thousandBaseSfp(12),
                        tenHundredBaseT4port(13),
                        tenHundredBaseFxMtrj4port(14),
                        comboStackingSfp(15),
                        tenHundredBaseT(16),
                        comboThousandBaseTxSfp(17),
                        eightPortSfpModule(18),
                        tenGigaPortModule(19),
                        hundredBaseScMcIfClassA(20),
                        hundredBaseScMcIfClassB(21)
                    }
        MAX-ACCESS  read-only
        STATUS      current
        DESCRIPTION "Type of expansion module in this switch slot 2."
        ::= { switchInfoEntry 12 }

swServiceTag OBJECT-TYPE
        SYNTAX      DisplayString (SIZE(0..80))
        MAX-ACCESS  read-only
        STATUS      current
        DESCRIPTION "Service tag serial-number of the switch."
        ::= { switchInfoEntry 13 }

swModelNumber OBJECT-TYPE
        SYNTAX      DisplayString (SIZE(0..15))
        MAX-ACCESS  read-only
        STATUS      current
        DESCRIPTION "Model number of the switch."
        ::= { switchInfoEntry 14 }

swEpldVer OBJECT-TYPE
        SYNTAX      DisplayString (SIZE(0..20))
        MAX-ACCESS  read-only
        STATUS      current
        DESCRIPTION "The EPLD version of the switch."
        ::= { switchInfoEntry 15 }

swExpectedModuleOpCodeVer OBJECT-TYPE
        SYNTAX      DisplayString (SIZE(0..15))
        MAX-ACCESS  read-only
        STATUS      current
        DESCRIPTION "The module opcode version reside in the switch, note that
                     this variable represent the desired version of the
                     module which might plug in. For version validation, only
                     the swExpectedModuleOpCodeVer of the master
                     is used. This object is compared with
                     the swModuleOpCodeVer of the master and all slaves."
        ::= { switchInfoEntry 16 }

switchOperState OBJECT-TYPE
        SYNTAX      INTEGER
                    {
                        other(1),
                        unknown(2),
                        ok(3),
                        noncritical(4),
                        critical(5),
                        nonrecoverable(6)
                    }
        MAX-ACCESS  read-only
        STATUS      current
        DESCRIPTION "Global operation state of the switch."
        ::= { switchMgt 4 }

switchProductId     OBJECT IDENTIFIER ::= { switchMgt 5 }

swProdName OBJECT-TYPE
        SYNTAX      DisplayString (SIZE(0..127))
        MAX-ACCESS  read-only
        STATUS      current
        DESCRIPTION "The product name of this switch."
        ::= { switchProductId 1 }

swProdManufacturer OBJECT-TYPE
        SYNTAX      DisplayString (SIZE(0..127))
        MAX-ACCESS  read-only
        STATUS      current
        DESCRIPTION "The product manufacturer of this switch."
        ::= { switchProductId 2 }

swProdDescription OBJECT-TYPE
        SYNTAX      DisplayString (SIZE(0..127))
        MAX-ACCESS  read-only
        STATUS      current
        DESCRIPTION "The product description of this switch."
        ::= { switchProductId 3 }

swProdVersion OBJECT-TYPE
        SYNTAX      DisplayString (SIZE(0..127))
        MAX-ACCESS  read-only
        STATUS      current
        DESCRIPTION "The runtime code version of this switch."
        ::= { switchProductId 4 }

swProdUrl OBJECT-TYPE
        SYNTAX      DisplayString (SIZE(0..127))
        MAX-ACCESS  read-only
        STATUS      current
        DESCRIPTION "The URL of this switch, which we can connect through
                     a web browser."
        ::= { switchProductId 5 }

swIdentifier OBJECT-TYPE
        SYNTAX      Integer32
        MAX-ACCESS  read-only
        STATUS      current
        DESCRIPTION "A unique identifier of which switch in the chassis is currently
                     being looked at."
        ::= { switchProductId 6 }

swChassisServiceTag OBJECT-TYPE
        SYNTAX      DisplayString (SIZE(0..80))
        MAX-ACCESS  read-only
        STATUS      current
        DESCRIPTION "The service tag of the chassis this switch resides in."
        ::= { switchProductId 7 }

switchIndivPowerTable OBJECT-TYPE
        SYNTAX      SEQUENCE OF SwitchIndivPowerEntry
        MAX-ACCESS  not-accessible
        STATUS      current
        DESCRIPTION "Table about the status of individual powers."
        ::= { switchMgt 6 }

switchIndivPowerEntry OBJECT-TYPE
        SYNTAX      SwitchIndivPowerEntry
        MAX-ACCESS  not-accessible
        STATUS      current
        DESCRIPTION "Table about the status of individual power."
        INDEX       { swIndivPowerUnitIndex, swIndivPowerIndex }
        ::= { switchIndivPowerTable 1 }

SwitchIndivPowerEntry ::= SEQUENCE
{
    swIndivPowerUnitIndex   Integer32,
    swIndivPowerIndex       INTEGER,
    swIndivPowerStatus      INTEGER,
    swIndivPowerType        INTEGER
}

swIndivPowerUnitIndex OBJECT-TYPE
        SYNTAX      Integer32
        MAX-ACCESS  accessible-for-notify
        STATUS      current
        DESCRIPTION "This is defined as swUnitIndex."
        ::= { switchIndivPowerEntry 1 }

swIndivPowerIndex OBJECT-TYPE
        SYNTAX      INTEGER
                    {
                      internalPower(1),
                      externalPower(2)
                    }
        MAX-ACCESS  accessible-for-notify
        STATUS      current
        DESCRIPTION "1 means internal power, 2 means external power."
        ::= { switchIndivPowerEntry 2 }

swIndivPowerStatus OBJECT-TYPE
        SYNTAX      INTEGER
                    {
                        notPresent(1),
                        green(2),
                        red(3)
                    }
        MAX-ACCESS  read-only
        STATUS      current
        DESCRIPTION "notPresent(1) means not present, green(2) means
                     up, red(3) means down."
        ::= { switchIndivPowerEntry 3 }

--
-- ASE3528B-E1-FLF-P5
--

swIndivPowerType OBJECT-TYPE
        SYNTAX      INTEGER
                    {
                        dc-n48(1),
                        dc-p27(2),
                        ac(3),
                        dc-n48-wrong(4),
                        dc-p27-wrong(5),
                        none(6),
                        ac-wrong(7)
                    }
        MAX-ACCESS  read-only
        STATUS      current
        DESCRIPTION "These parameters indicate the power type used by the module.
                     The value dc-n48(1) means that the power module uses DC-N48 as power input.
                     The value dc-p27(2) means that the power module uses DC-P27 as power input.
                     The value ac means that the power module uses AC as power input.
                     The value dc-n48-wrong(4) means that the power module currently
                     uses DC-N48 as power input but the module is inconsistent with another
                     power module. The value dc-p27-wrong(5) means that the power module
                     currently uses DC-P27 as power input but the module is inconsistent with
                     with another power module. The value none(6) means that the power module
                     is not present. The value ac-wrong(7) means that the power module
                     currently uses AC as power input but the module is inconsistent with
                     another power module."
	  ::= { switchIndivPowerEntry 4 }

switchJumboFrameStatus OBJECT-TYPE
         SYNTAX     EnabledStatus
         MAX-ACCESS read-write
         STATUS     current
         DESCRIPTION "enabled(1) means the Jumbo Frame is enabled, disabled(2)
                     means the Jumbo Frame is disabled."
         ::= { switchMgt 7 }

-- Unicorn only(Darwin add amtrmgt too)
amtrMgt      OBJECT IDENTIFIER   ::= { switchMgt 8 }
-- Address Management

amtrMacAddrRisingThreshold OBJECT-TYPE
         SYNTAX     Integer32
         MAX-ACCESS read-write
         STATUS     current
         DESCRIPTION "Rising threshold for swMacAddressTrap, when the MAC
                      address entry exceeds this value, a swMacAddressTrap
                      will be sent, note, once this trap has been sent, the
                      next trigger time for this trap is after the MAC
                      address entry has fallen below the amtrMacAddrFallingThreshold,
                      and exceeds the rising threshold again."
         ::= { amtrMgt 1 }

amtrMacAddrFallingThreshold OBJECT-TYPE
         SYNTAX     Integer32
         MAX-ACCESS read-write
         STATUS     current
         DESCRIPTION "Falling threshold for swMacAddressTrap, once the trap
                      has been triggered, the next trap will send only when the
                      entry has fallen below this threshold and exceeds the amtrMac-
                      AddrRisingThreshold."
         ::= { amtrMgt 2 }

amtrMacAddrAgingStatus OBJECT-TYPE
         SYNTAX     EnabledStatus
         MAX-ACCESS read-write
         STATUS     current
         DESCRIPTION "If this is enabled(1), the MAC address table will age out according to
                      its timer. If this is disabled(2), the MAC address table will not
                      age out."
         ::= { amtrMgt 3 }

--ASE3528B-E1-FLF-P5-00029
amtrMacAddrDynamicCount OBJECT-TYPE
         SYNTAX     Counter32
         MAX-ACCESS read-only
         STATUS     current
         DESCRIPTION
             "The number of dot1dTpFdbTable entries in the BRIDGE-MIB."
         ::= { amtrMgt 4 }

--ASE3528B-E1-FLF-P5-00029
amtrMacAddrStaticCount OBJECT-TYPE
         SYNTAX     Counter32
         MAX-ACCESS read-only
         STATUS     current
         DESCRIPTION
             "The number of dot1dStaticTable entries in  the BRIDGE-MIB."
         ::= { amtrMgt 5 }

--ASE3528B-E1-FLF-P5-00029
amtrMacAddrTotalCount OBJECT-TYPE
         SYNTAX     Counter32
         MAX-ACCESS read-only
         STATUS     current
         DESCRIPTION
             "The sum of dot1dTpFdbTable and dot1dStaticTable entries."
         ::= { amtrMgt 6 }

--switchFanTable
switchFanTable OBJECT-TYPE
       SYNTAX      SEQUENCE OF SwitchFanEntry
       MAX-ACCESS  not-accessible
       STATUS      current
       DESCRIPTION "The fan status table."
       ::= { switchMgt 9 }

switchFanEntry OBJECT-TYPE
       SYNTAX      SwitchFanEntry
       MAX-ACCESS  not-accessible
       STATUS      current
       DESCRIPTION "A conceptual row of the switchFanTable."
       INDEX  { switchUnitIndex, switchFanIndex }
       ::= { switchFanTable 1 }

SwitchFanEntry ::= SEQUENCE
{
    switchUnitIndex     Integer32,
    switchFanIndex      Integer32,
    switchFanStatus     INTEGER,
    switchFanAdminSpeed Integer32,
    switchFanFailureCount Integer32,
    switchFanOperSpeed    Integer32
}

switchUnitIndex OBJECT-TYPE
       SYNTAX      Integer32
       MAX-ACCESS  accessible-for-notify
       STATUS      current
       DESCRIPTION "The unit of the switch for the stackable device."
       ::= { switchFanEntry 1 }

switchFanIndex OBJECT-TYPE
       SYNTAX      Integer32
       MAX-ACCESS  accessible-for-notify
       STATUS      current
       DESCRIPTION "The unit number of the fan."
       ::= { switchFanEntry 2 }

switchFanStatus OBJECT-TYPE
       SYNTAX   INTEGER
                {
                    ok(1),
                    failure(2)
                }
       MAX-ACCESS  read-only
       STATUS      current
       DESCRIPTION "Indicating the status of the fan, 1:ok; 2:failure."
       ::= { switchFanEntry 3 }

switchFanAdminSpeed OBJECT-TYPE
       SYNTAX   Integer32
       MAX-ACCESS  read-write
       STATUS      current
       DESCRIPTION "The speed of the fan, measured in rpm (rotations per
                    minute). Set this object to 0 to enter auto mode,
                    set to other values to enter manual mode."
       ::= { switchFanEntry 4 }

switchFanFailureCount OBJECT-TYPE
       SYNTAX      Integer32
       MAX-ACCESS  read-only
       STATUS      current
       DESCRIPTION "The total failure count of the fan since the switch
                    has reboot."
       ::= { switchFanEntry 5 }

switchFanOperSpeed OBJECT-TYPE
       SYNTAX   Integer32
       MAX-ACCESS  read-only
       STATUS      current
       DESCRIPTION "The operational value of the fan speed, measured in rpm (rotations per
                    minute)."
       ::= { switchFanEntry 6 }

switchLoopbackTestFailurePorts OBJECT-TYPE
       SYNTAX      OCTET STRING
       MAX-ACCESS  read-only
       STATUS      current
       DESCRIPTION "The Loopback test failure port list."
       ::= { switchMgt 10 }

-- switchThermalTempTable

switchThermalTempTable OBJECT-TYPE
       SYNTAX      SEQUENCE OF SwitchThermalTempEntry
       MAX-ACCESS  accessible-for-notify
       STATUS      current
       DESCRIPTION "The table which collects switch temperature information."
       ::= { switchMgt 11 }

switchThermalTempEntry OBJECT-TYPE
       SYNTAX      SwitchThermalTempEntry
       MAX-ACCESS  accessible-for-notify
       STATUS      current
       DESCRIPTION "A conceptual row of the switchThermalTempTable."
       INDEX  { switchThermalTempUnitIndex,switchThermalTempThermalIndex}
       ::= { switchThermalTempTable 1 }

SwitchThermalTempEntry ::= SEQUENCE
{
    switchThermalTempUnitIndex          Integer32,
    switchThermalTempThermalIndex       Integer32,
    switchThermalTempValue              Integer32
}

switchThermalTempUnitIndex OBJECT-TYPE
       SYNTAX      Integer32
       MAX-ACCESS  accessible-for-notify
       STATUS      current
       DESCRIPTION "The unit of the switch for stackable device."
       ::= { switchThermalTempEntry 1 }

switchThermalTempThermalIndex OBJECT-TYPE
       SYNTAX      Integer32
       MAX-ACCESS  accessible-for-notify
       STATUS      current
       DESCRIPTION "The thermal index of the switch."
       ::= { switchThermalTempEntry 2 }

switchThermalTempValue OBJECT-TYPE
       SYNTAX      Integer32
       MAX-ACCESS  read-only
       STATUS      current
       DESCRIPTION "The temperature of the device in degrees Celsius."
       ::= { switchThermalTempEntry 3 }

--switchThermalActionTable
switchThermalActionTable OBJECT-TYPE
       SYNTAX      SEQUENCE OF SwitchThermalActionEntry
       MAX-ACCESS  not-accessible
       STATUS      current
       DESCRIPTION "The table for configuring the thermal action."
       ::= { switchMgt 12 }

switchThermalActionEntry OBJECT-TYPE
       SYNTAX      SwitchThermalActionEntry
       MAX-ACCESS  not-accessible
       STATUS      current
       DESCRIPTION "A conceptual row of the switchThermalActionTable."
       INDEX  { switchThermalActionUnitIndex,switchThermalActionThermalIndex,
                switchThermalActionIndex }
       ::= { switchThermalActionTable 1 }

SwitchThermalActionEntry ::= SEQUENCE
{
    switchThermalActionUnitIndex        Integer32,
    switchThermalActionThermalIndex     Integer32,
    switchThermalActionIndex            Integer32,
    switchThermalActionRisingThreshold  Integer32,
    switchThermalActionFallingThreshold Integer32,
    switchThermalActionAction           BITS,
    switchThermalActionStatus           ValidStatus
}

switchThermalActionUnitIndex OBJECT-TYPE
       SYNTAX      Integer32
       MAX-ACCESS  accessible-for-notify
       STATUS      current
       DESCRIPTION "The unit of the switch for stackable device."
       ::= { switchThermalActionEntry 1 }

switchThermalActionThermalIndex OBJECT-TYPE
       SYNTAX      Integer32
       MAX-ACCESS  accessible-for-notify
       STATUS      current
       DESCRIPTION "The thermal index of the switch."
       ::= { switchThermalActionEntry 2 }

switchThermalActionIndex OBJECT-TYPE
       SYNTAX      Integer32
       MAX-ACCESS  accessible-for-notify
       STATUS      current
       DESCRIPTION "The action index of the switchTheramlActionTable."
       ::= { switchThermalActionEntry 3 }

switchThermalActionRisingThreshold OBJECT-TYPE
       SYNTAX      Integer32
       MAX-ACCESS  read-create
       STATUS      current
       DESCRIPTION "The rising threshold of the switch temperature."
       ::= { switchThermalActionEntry 4 }

switchThermalActionFallingThreshold OBJECT-TYPE
       SYNTAX      Integer32
       MAX-ACCESS  read-create
       STATUS      current
       DESCRIPTION "The falling threshold of the switch temperature."
       ::= { switchThermalActionEntry 5 }

switchThermalActionAction OBJECT-TYPE
       SYNTAX      BITS {
                            trap(0)
                        }
       MAX-ACCESS  read-create
       STATUS      current
       DESCRIPTION "The action that will be taken when the
                    temperature exceeds the rising threshold
                    or falls below the falling threshold."
       ::= { switchThermalActionEntry 6 }

switchThermalActionStatus OBJECT-TYPE
       SYNTAX      ValidStatus
       MAX-ACCESS  read-create
       STATUS      current
       DESCRIPTION "Set valid(1) to create an entry, Set Invalid(2) to delete an entry."
       ::= { switchThermalActionEntry 7 }

switchModuleInfoTable OBJECT-TYPE
        SYNTAX      SEQUENCE OF SwitchModuleInfoEntry
        MAX-ACCESS  not-accessible
        STATUS      current
        DESCRIPTION "Table of descriptive and status information about
                     the switch modules in this system."
        ::= { switchMgt 13 }

switchModuleInfoEntry OBJECT-TYPE
        SYNTAX      SwitchModuleInfoEntry
        MAX-ACCESS  not-accessible
        STATUS      current
        DESCRIPTION "Table providing descriptions and status information for
                     switch modules."
        INDEX       { swModuleUnitIndex, swModuleModuleIndex }
        ::= { switchModuleInfoTable 1 }

SwitchModuleInfoEntry ::= SEQUENCE
{
    swModuleUnitIndex       Integer32,
    swModuleModuleIndex     Integer32,
    swModuleHardwareVer     DisplayString,
    swModuleMicrocodeVer    DisplayString,
    swModuleLoaderVer       DisplayString,
    swModuleBootRomVer      DisplayString,
    swModuleOpCodeVer       DisplayString,
    swModulePortNumber      Integer32,
    swModuleSerialNumber    DisplayString,
    swModuleType            INTEGER,
    swModuleModelNumber     DisplayString,
    swModuleEpldVer         DisplayString,
    swModuleDescr           DisplayString,
    swModuleXenpakType      INTEGER
}

swModuleUnitIndex OBJECT-TYPE
        SYNTAX      Integer32
        MAX-ACCESS  not-accessible
        STATUS      current
        DESCRIPTION "This object identifies the switch within the system
                     for which this entry contains information. This
                     value can never be greater than switchNumber."
        ::= { switchModuleInfoEntry 1 }

swModuleModuleIndex OBJECT-TYPE
        SYNTAX      Integer32
        MAX-ACCESS  not-accessible
        STATUS      current
        DESCRIPTION "This object identifies the module within the switch
                     for which this entry contains information."
        ::= { switchModuleInfoEntry 2 }

swModuleHardwareVer OBJECT-TYPE
        SYNTAX      DisplayString (SIZE(0..20))
        MAX-ACCESS  read-only
        STATUS      current
        DESCRIPTION "Hardware version of the module board."
        ::= { switchModuleInfoEntry 3 }

swModuleMicrocodeVer OBJECT-TYPE
        SYNTAX      DisplayString (SIZE(0..20))
        MAX-ACCESS  read-only
        STATUS      current
        DESCRIPTION "Microcode version of the module board."
        ::= { switchModuleInfoEntry 4 }

swModuleLoaderVer OBJECT-TYPE
        SYNTAX      DisplayString (SIZE(0..20))
        MAX-ACCESS  read-only
        STATUS      current
        DESCRIPTION "Loader version of the module board."
        ::= { switchModuleInfoEntry 5 }

swModuleBootRomVer OBJECT-TYPE
        SYNTAX      DisplayString (SIZE(0..20))
        MAX-ACCESS  read-only
        STATUS      current
        DESCRIPTION "Boot ROM code version of the module board."
        ::= { switchModuleInfoEntry 6 }

swModuleOpCodeVer OBJECT-TYPE
        SYNTAX      DisplayString (SIZE(0..20))
        MAX-ACCESS  read-only
        STATUS      current
        DESCRIPTION "Operation code version of the module board."
        ::= { switchModuleInfoEntry 7 }

swModulePortNumber OBJECT-TYPE
        SYNTAX      Integer32
        MAX-ACCESS  read-only
        STATUS      current
        DESCRIPTION "The number of ports of this module."
        ::= { switchModuleInfoEntry 8 }

swModuleSerialNumber OBJECT-TYPE
        SYNTAX      DisplayString (SIZE(0..80))
        MAX-ACCESS  read-only
        STATUS      current
        DESCRIPTION "Serial number of the module."
        ::= { switchModuleInfoEntry 9 }

swModuleType OBJECT-TYPE
        SYNTAX      INTEGER
                    {
                        notPresent(1),
                        other(2),
                        hundredBaseFxScMmf(3),
                        hundredBaseFxScSmf(4),
                        hundredBaseFxMtrjMmf(5),
                        thousandBaseSxScMmf(6),
                        thousandBaseSxMtrjMmf(7),
                        thousandBaseXGbic(8),
                        thousandBaseLxScSmf(9),
                        thousandBaseT(10),
                        stackingModule(11),
                        thousandBaseSfp(12),
                        tenHundredBaseT4port(13),
                        tenHundredBaseFxMtrj4port(14),
                        comboStackingSfp(15),
                        tenHundredBaseT(16),
                        comboThousandBaseTxSfp(17),
                        eightPortSfpModule(18),
                        tenGigaPortModule(19)
                    }
        MAX-ACCESS  read-only
        STATUS      current
        DESCRIPTION "Type of module."
        ::= { switchModuleInfoEntry 10 }

swModuleModelNumber OBJECT-TYPE
        SYNTAX      DisplayString (SIZE(0..15))
        MAX-ACCESS  read-only
        STATUS      current
        DESCRIPTION "Model number of the module."
        ::= { switchModuleInfoEntry 11 }

swModuleEpldVer  OBJECT-TYPE
        SYNTAX      DisplayString (SIZE(0..20))
        MAX-ACCESS  read-only
        STATUS      current
        DESCRIPTION "The EPLD version of the module."
        ::= { switchModuleInfoEntry 12 }

swModuleDescr OBJECT-TYPE
        SYNTAX      DisplayString (SIZE(0..255))
        MAX-ACCESS  read-only
        STATUS      current
        DESCRIPTION " A textual description of the entity to describe the
                     module."
        ::= { switchModuleInfoEntry 13 }

swModuleXenpakType OBJECT-TYPE
        SYNTAX      INTEGER
                    {
                        notPresent(1),
                        unknown(2),
                        unsupportedLR(3),
                        unsupportedER(4),
                        unsupportedCX4(5),
                        supportedLR(6),
                        supportedER(7),
                        supportedCX4(8)
                    }
        MAX-ACCESS  read-only
        STATUS      current
        DESCRIPTION "If the corresponding swModuleType(10) is not
                     tenGigaPortModule(19), then this variable is
                     notPresent(1). If the corresponding swModuleType(10)
                     is tenGigaPortModule(19), then this variable
                     represents the type of Xenpak module."
        ::= { switchModuleInfoEntry 14 }

switchRenumberUnitID OBJECT-TYPE
        SYNTAX      INTEGER
                    {
                        renumber(1),
                        noRenumber(2)
                    }
        MAX-ACCESS  read-write
        STATUS      current
        DESCRIPTION "The value renumber will automatically assign an ID to
                     units in the stack; all UNIT IDs will be contiguous.
                     The system configurations are not changed but the system
                     will restart after renumbering is completed."
        ::= { switchMgt 14 }

switchConfigAutosaveEnableStatus OBJECT-TYPE
        SYNTAX      EnabledStatus
        MAX-ACCESS  read-write
        STATUS      current
        DESCRIPTION "Set this object to enabled(1) to enable configuration
                     autosave. Set this object to disabled(2) to disable
                     configuration autosave. After you set it to disabled(2),
                     you need to wait until switchConfigAutosaveBusyStatus
                     is notBusy(2), indicating that autosave has stopped."
        ::= { switchMgt 15 }

switchConfigAutosaveBusyStatus OBJECT-TYPE
        SYNTAX      INTEGER
                    {
                        busy(1),
                        notBusy(2)
                    }
        MAX-ACCESS  read-only
        STATUS      current
        DESCRIPTION "If this object is busy(1), it means that the system
                     has not finished saving all configurations non-volatile
                     memory. If this object is notBusy(2), it means that
                     the system has finished saving all configurations to
                     non-volatile memory. After you set
                     switchConfigAutosaveEnableStatus to disabled(2),
                     you need to wait until switchConfigAutosaveBusyStatus
                     is notBusy(2), indicating that autosave has stopped."
        ::= { switchMgt 16 }

--ASE3528B-E1-FLF-P5-00070
switchFanFailureNum	OBJECT-TYPE
    	SYNTAX      Integer32
    	MAX-ACCESS  read-only
    	STATUS      current
    	DESCRIPTION "This variable is used to display total number of
                     nonfuncitonal fans."
          ::= { switchMgt 17 }

--
-- portMgt
--

-- Management ports. This group also provides information
-- related to trunks because they share the same properties.

portTable OBJECT-TYPE
        SYNTAX      SEQUENCE OF PortEntry
        MAX-ACCESS  not-accessible
        STATUS      current
        DESCRIPTION "Table of descriptive and status information describing
                     the configuration of each switch port. This table also
                     contains information about each trunk."
        ::= { portMgt 1 }

portEntry OBJECT-TYPE
        SYNTAX      PortEntry
        MAX-ACCESS  not-accessible
        STATUS      current
        DESCRIPTION "An entry in the table, describing the configuration of
                     one switch port or trunk."
        INDEX       { portIndex }
        ::= { portTable 1 }

PortEntry ::= SEQUENCE
{
    portIndex                Integer32,
    portName                 DisplayString,
    portType                 INTEGER,
    portSpeedDpxCfg          INTEGER,
    portFlowCtrlCfg          INTEGER,
    portCapabilities         BITS,
    portAutonegotiation      EnabledStatus,
    portSpeedDpxStatus       INTEGER,
    portFlowCtrlStatus       INTEGER,
    portTrunkIndex           Integer32,
    portEthernetType         INTEGER,
    portComboForcedMode      INTEGER,
    portPrivateMode          INTEGER,
    portMdixMode             INTEGER
}

portIndex OBJECT-TYPE
        SYNTAX      Integer32
        MAX-ACCESS  not-accessible
        STATUS      current
        DESCRIPTION "The port and the trunk (including trunk members) interface of
                     the portTable. The interface identified by a particular value
                     of this index is the same interface as identified by the same
                     value of ifIndex in the IF-MIB."
        ::= { portEntry 1 }

portName OBJECT-TYPE
        SYNTAX      DisplayString (SIZE(0..64))
        MAX-ACCESS  read-write
        STATUS      current
        DESCRIPTION "The name of the port or trunk. This is the same as ifAlias
                     in the IF-MIB (RFC2863 or later)."
        ::= { portEntry 2 }

portType OBJECT-TYPE
        SYNTAX      INTEGER
                    {
                        other(1),
                        hundredBaseTX(2),
                        hundredBaseFX(3),
                        thousandBaseSX(4),
                        thousandBaseLX(5),
                        thousandBaseT(6),
                        thousandBaseGBIC(7),
                        thousandBaseSfp(8),
                        hundredBaseFxScSingleMode(9),
                        hundredBaseFxScMultiMode(10),
                        thousandBaseCX(11),
                        tenG(12)
                    }
        MAX-ACCESS  read-only
        STATUS      current
        DESCRIPTION "Indicates the port type of the configuration of the switch."
        ::= { portEntry 3 }

portSpeedDpxCfg OBJECT-TYPE
        SYNTAX      INTEGER
                    {
                        reserved(1),
                        halfDuplex10(2),
                        fullDuplex10(3),
                        halfDuplex100(4),
                        fullDuplex100(5),
                        halfDuplex1000(6),
                        fullDuplex1000(7),
                        halfDuplex10g(8),
                        fullDuplex10g(9)
                    }
        MAX-ACCESS  read-write
        STATUS      current
        DESCRIPTION "Configures the speed and duplex mode for a port or trunk,
                     according to:
                         halfDuplex10(2)    - 10Mbps and half duplex mode
                         fullDuplex10(3)    - 10Mbps and full duplex mode
                         halfDuplex100(4)   - 100Mbps and half duplex mode
                         fullDuplex100(5)   - 100Mbps and full duplex mode
                         halfDuplex1000(6)  - 1000Mbps and half duplex mode
                         fullDuplex1000(7)  - 1000Mbps and full duplex mode
                         halfDuplex10g(8)   - 10g and half duplex mode
                         fullDuplex10g(9)   - 10g and full duplex mode

                        hundredBaseTX  port can be set as:
                            halfDuplex10(2)
                            fullDuplex10(3)
                            halfDuplex100(4)
                            fullDuplex100(5)
                        hundredBaseFX  port can be set as:
                            fullDuplex100(5)
                        thousandBaseSX port can be set as:
                            fullDuplex1000(7)
                        thousandBaseLX port can be set as:
                            fullDuplex1000(7)
                        thousandBaseT port can be set as:
                            halfDuplex10(2)
                            fullDuplex10(3)
                            halfDuplex100(4)
                            fullDuplex100(5)
                        thousandBaseGBIC port can be set as:
                            fullDuplex1000(7)
                        thousandBaseSfp port can be set as:
                            fullDuplex1000(7)
                        hundredBaseFxScSingleMode port can be set as:
                            fullDuplex100(5)
                        hundredBaseFxScMultiMode port can be set as:
                            fullDuplex100(5)
                        thousandBaseCX port can be set as:
                            fullDuplex1000(7)
                        tenG port can be set as:
                            halfDuplex10g(8)
                            fullDuplex10g(9)

                     The actual operating speed and duplex of the port
                     is given by portSpeedDpxStatus."
        DEFVAL      { halfDuplex10 }
        ::= { portEntry 4 }

portFlowCtrlCfg OBJECT-TYPE
        SYNTAX      INTEGER
                    {
                        enabled(1),
                        disabled(2),
                        tx(5),
                        rx(6)
                    }
        MAX-ACCESS  read-write
        STATUS      current
        DESCRIPTION "(1) Flow control mechanism is enabled with tx and rx pause
                         mechansim.
                         If the port type is hundredBaseTX or thousandBaseSX:
                         When the port is operating in halfDuplex mode, the
                         port uses backPressure flow control mechanism. When
                         the port is operating in fullDuplex mode, the port
                         uses IEEE 802.3x flow control mechanism.
                         If the port type is hundredBaseFX:
                         When the port is operating in halfDuplex mode, the
                         port uses backPressure flow control mechanism. When
                         the port is operating in fullDuplex mode, Flow
                         control mechanism will not function.
                     (2) Flow control mechanism is disabled.
                     (5) Flow control mechanism is enabled with tx pause
                         mechanism only.
                     (6) Flow control mechansim is enabled with rx pause
                         mechansim only.

                     Fast ethernet ports can be set as:
                         enabled(1),
                         disabled(2).
                     Gigabit ethernet ports can be set as:
                         enabled(1),
                         disabled(2),
                         tx(5),
                         rx(6).
                     The actual flow control mechanism is used given by
                     portFlowCtrlStatus."
        DEFVAL      { enabled }
        ::= { portEntry 5 }

portCapabilities OBJECT-TYPE
        SYNTAX      BITS
                    {
                        portCap10half(0),
                        portCap10full(1),
                        portCap100half(2),
                        portCap100full(3),
                        portCap1000half(4),
                        portCap1000full(5),
                        portCap10gHalf(6),
                        portCap10gFull(7),
                        reserved8(8),
                        reserved9(9),
                        reserved10(10),
                        reserved11(11),
                        reserved12(12),
                        reserved13(13),
                        portCapSym(14),
                        portCapFlowCtrl(15)
                    }
        MAX-ACCESS  read-write
        STATUS      current
        DESCRIPTION "Port or trunk capabilities."
        ::= { portEntry 6 }

portAutonegotiation OBJECT-TYPE
        SYNTAX      EnabledStatus
        MAX-ACCESS  read-write
        STATUS      current
        DESCRIPTION "Whether auto-negotiation is enabled."
        ::= { portEntry 7 }

portSpeedDpxStatus OBJECT-TYPE
        SYNTAX      INTEGER
                    {
                        error(1),
                        halfDuplex10(2),
                        fullDuplex10(3),
                        halfDuplex100(4),
                        fullDuplex100(5),
                        halfDuplex1000(6),
                        fullDuplex1000(7),
                        halfDuplex10g(8),
                        fullDuplex10g(9)
                    }
        MAX-ACCESS  read-only
        STATUS      current
        DESCRIPTION "The operating speed and duplex mode of the
                     switched port or trunk. If the entry represents a trunk,
                     the speed is that of its individual members unless
                     the member ports have been inconsistently configured
                     in which case the value is error(1)."
        ::= { portEntry 8 }

portFlowCtrlStatus OBJECT-TYPE
        SYNTAX      INTEGER
                    {
                        error(1),
                        backPressure(2),
                        dot3xFlowControl(3),
                        none(4)
                    }
        MAX-ACCESS  read-only
        STATUS      current
        DESCRIPTION "(2) BackPressure flow control mechanism is used.
                     (3) IEEE 802.3 flow control mechanism is used.
                     (4) Flow control mechanism is disabled.
                     If the entry represents a trunk and the member ports
                     have been inconsistently configured then this value
                     is error(1)."
        ::= { portEntry 9 }

portTrunkIndex OBJECT-TYPE
        SYNTAX      Integer32
        MAX-ACCESS  read-only
        STATUS      current
        DESCRIPTION "The trunk to which this port belongs. A value of 0
                    means that this port does not belong to any trunk.
                    A value greater than zero means that this port
                    belongs to a trunk in the trunkIndex, defined by the
                    corresponding trunkPorts."
        ::= { portEntry 10 }

-- for VDSL only
portEthernetType OBJECT-TYPE
       SYNTAX     INTEGER
                  {
                   other(1),
                   normal(2),
                   ethernetFirstMile(3)
                  }
       MAX-ACCESS read-only
       STATUS     current
       DESCRIPTION "The type of ethernet. other(1) means not recognized.
                    normalEthernet(2) means normal. ethernetFirstMile means
                    ethernetFirstMile (EFM) for VDSL."
       ::= { portEntry 11}

portComboForcedMode  OBJECT-TYPE
       SYNTAX     INTEGER
                  {
                    none(1),
                    copperForced(2),
                    copperPreferredAuto(3),
                    sfpForced(4),
                    sfpPreferredAuto(5),
                    hundredFullForced(6)
                  }
       MAX-ACCESS read-write
       STATUS     current
       DESCRIPTION "This determines the running mode of a combo port.
                    For a non-combo port, this variable has a value of none(1),
                    and setting this variable to none(1) has no effect.
                    For a combo port, this has its own valid values not
                    equal to none(1), and setting this variable to none(1) is
                    not allowed. copperForced(2) is set if user want to force
                    this combo port running in copper mode. copperPreferredAuto(3)
                    is obsoleted, and user shall not set this state. sfpForced(4)
                    is set if user want to force this combo port running in fiber
                    mode. sfpPreferredAuto(5) is set if user want to change copper or
                    fiber mode automatically by SFP transceiver present state. If SFP
                    transceiver is present, this combo port will run in fiber mode, and
                    if SFP transceiver is not present, this combo port will run in
                    copper mode. hundredFullForced(6) is set if user want to force
                    this combo port running in hundred full mode."
       ::= { portEntry 12}

portPrivateMode OBJECT-TYPE
        SYNTAX      INTEGER
                    {
                        enabled (1),
                        disabled (2),
                        notAvailable (3)
                    }
        MAX-ACCESS  read-write
        STATUS      current
        DESCRIPTION "This object specifies whether or not the port is operating
                     in Private mode. If enabled, all traffic to and from other
                     ports configured in Private Mode is disabled. Traffic will
                     pass normally between a 'private' port and a 'public' port.
                     No data will pass between ports configured in 'private' mode.
                     If disabled, traffic flows normally to and from the port.
                     A value of notAvailable indicates that the port does not
                     support this feature. notAvailable (3) is a read-only value,
                     which will be rejected with an SNMP 'bad value' error code
                     if the user tries to write this value."
        ::= { portEntry 13 }

portMdixMode OBJECT-TYPE
        SYNTAX      INTEGER
                    {
                        auto(1),
                        straight(2),
                        crossover(3)
                    }
        MAX-ACCESS  read-write
        STATUS      current
        DESCRIPTION "This parameter can be configured to auto(1), which means the
                     connection mode will be auto detected; straight(2), which means
                     the connection is used the straight-through twisted pair cabling;
                     and crossover(3), which means the connection is used the crossover
                     twisted pair cabling."
        ::= { portEntry 14 }

portLoopBackTestTable OBJECT-TYPE
        SYNTAX      SEQUENCE OF PortLoopBackTestEntry
        MAX-ACCESS  not-accessible
        STATUS      current
        DESCRIPTION "The Table for Loop Back Test."
        ::= { portMgt 2 }

portLoopBackTestEntry OBJECT-TYPE
        SYNTAX      PortLoopBackTestEntry
        MAX-ACCESS  not-accessible
        STATUS      current
        DESCRIPTION "The conceptual row of portLoopBackTestTable."
        INDEX       { portLoopBackTestIndex }
        ::= { portLoopBackTestTable 1 }

PortLoopBackTestEntry ::= SEQUENCE
{
    portLoopBackTestIndex    Integer32,
    portLoopBackTestAction   INTEGER,
    portLoopBackTestResult   INTEGER
}

portLoopBackTestIndex OBJECT-TYPE
        SYNTAX      Integer32
        MAX-ACCESS  not-accessible
        STATUS      current
        DESCRIPTION "This is defined as ifIndex in the IF-MIB."
        ::= { portLoopBackTestEntry 1 }

portLoopBackTestAction OBJECT-TYPE
       SYNTAX    INTEGER
                 {
                   noLoopBackTest(1),
                   loopBackTestShort(2),
                   loopBackTestLong(3)
                 }
       MAX-ACCESS read-write
       STATUS     current
       DESCRIPTION "Set loopBackTestStartShort to perform the short loopback test.
                    Set loopBackTestLong to perform the long loopback test.
                    When read, always return noLoopBackTest(1)."
       ::= { portLoopBackTestEntry 2 }

portLoopBackTestResult OBJECT-TYPE
       SYNTAX    INTEGER
                 {
                   notTesting(1),
                    reserved(2),
                    frameSetTimeout(3),
                    frameTimeout(4),
                    releaseCmdTimeout(5),
                    normalityEnd(6),
                    umcTimeout(7),
                    busy(8)
                 }
        MAX-ACCESS read-only
        STATUS     current
        DESCRIPTION "The result of the last loopback test, when no loopback test
                     is being performed, will get notTesting(1)."
        ::= { portLoopBackTestEntry 3}

--
-- trunkMgt
--

-- Trunks: Provides additional information for Trunks


trunkMaxId OBJECT-TYPE
    SYNTAX      Integer32
    MAX-ACCESS  read-only
    STATUS      current
    DESCRIPTION
        "The maximum number for a trunk identifier."
    ::= { trunkMgt 1 }

trunkValidNumber OBJECT-TYPE
    SYNTAX      Integer32
    MAX-ACCESS  read-only
    STATUS      current
    DESCRIPTION
        "The number of valid trunks."
    ::= { trunkMgt 2 }

trunkTable OBJECT-TYPE
        SYNTAX      SEQUENCE OF TrunkEntry
        MAX-ACCESS  not-accessible
        STATUS      current
        DESCRIPTION "Table describing the configuration and status of each
                     trunk."
        ::= { trunkMgt 3 }

trunkEntry OBJECT-TYPE
        SYNTAX      TrunkEntry
        MAX-ACCESS  not-accessible
        STATUS      current
        DESCRIPTION "An entry describing the configuration and status of a
                     particular trunk."
        INDEX       { trunkIndex }
        ::= { trunkTable 1 }

TrunkEntry ::= SEQUENCE
{
    trunkIndex                Integer32,
    trunkPorts                PortList,
    trunkCreation             INTEGER,
    trunkStatus               ValidStatus,
-- ACD only
    trunkGroup                Integer32,
-- ACD3508n only
    trunkGroup8p              Integer32
}

trunkIndex OBJECT-TYPE
        SYNTAX      Integer32
        MAX-ACCESS  not-accessible
        STATUS      current
        DESCRIPTION "Identifies the trunk within the switch that is
                     described by the table entry."
        ::= { trunkEntry 1 }

trunkPorts OBJECT-TYPE
    SYNTAX      PortList
    MAX-ACCESS  read-create
    STATUS      current
    DESCRIPTION
        "The complete set of ports currently associated with
        this trunk."
    ::= { trunkEntry 2 }

trunkCreation OBJECT-TYPE
    SYNTAX      INTEGER
                {
                    static(1),
                    lacp(2)
                }
    MAX-ACCESS  read-only
    STATUS      current
    DESCRIPTION
        "A value of static(1) means a statically configured trunk.
         A value of lacp(2) means an LACP-configured trunk."
    ::= { trunkEntry 3 }

trunkStatus OBJECT-TYPE
    SYNTAX      ValidStatus
    MAX-ACCESS  read-create
    STATUS      current
    DESCRIPTION
        "Writing this to valid(1) creates an entry.
         Writing this to invalid(2) destroys an entry.
         A trunk created by LACP cannot be manually destroyed
         or (re)configured."
    ::= { trunkEntry 4 }

trunkGroup OBJECT-TYPE
    SYNTAX       Integer32(0..10)
    MAX-ACCESS   read-create
    STATUS       current
    DESCRIPTION "The trunk group, none(0) means no ports in the
                 trunk. Setting to none(0) removes a group in a trunk.
                 group 1 to group 10 have the following relationships.
                 Group 1: -> Port 1, 13,
                 Group 2:-> Port 1,2,13,14
                 Group 3: -> Port 1,2,3,4,13,14,15,16
                 Group 4: -> Port 5,17
                 Group 5: -> Port 5,6,17,18
                 Group 6: -> Port 5,6,7,8,17,18,19,20
                 Group 7: -> Port 9,21 Group 8: -> Port 9,10,21,22
                 Group 9: -> Port 9,10,11,12,21,22,23,24
                 Group 10: -> Port 25,26."
    ::= { trunkEntry 5 }

trunkGroup8p OBJECT-TYPE
    SYNTAX       Integer32(0..6)
    MAX-ACCESS   read-create
    STATUS       current
    DESCRIPTION "The trunk group, none(0) means no ports in the
                 trunk. Setting to none(0) removes a group in a trunk.
                 group 1 to group 6 have the following relationships.
                 Group 1: -> Port 1-2 Group 2: -> Port 3-4 Group 3: -> Port 5-6
                 Group 4: -> Port 7-8 Group 5: -> Port 1-4 Group 6: -> Port 5-8."
    ::= { trunkEntry 6 }

trunkBalanceMode OBJECT-TYPE
    SYNTAX  INTEGER
    {
        macSrc(1),
        macDst(2),
        macSrcDst(3),
        ipSrc(4),
        ipDst(5),
        ipSrcDst(6)
    }
    MAX-ACCESS  read-create
    STATUS      current
    DESCRIPTION "This defines the load balancing mode of trunks
                in the system. It may be based on source and/or
                destination MAC address or IP address.
                macSrc(1) means source MAC address.
                macDst(2) means destination MAC address.
                macSrcDst(3) means source and destination MAC address.
                ipSrc(4) means source IP address.
                ipDst(5) means destination IP address.
                ipSrcDst(6) means source and destination IP address."
    ::= { trunkMgt 4 }

---
--- lacpMgt
---

-- Management for Link Aggregation Control Protocol (LACP, 802.3ad),
-- that is dynamic trunking.

lacpPortTable OBJECT-TYPE
        SYNTAX      SEQUENCE OF LacpPortEntry
        MAX-ACCESS  not-accessible
        STATUS      current
        DESCRIPTION "Table for LACP port configuration."
        ::= { lacpMgt 1 }

lacpPortEntry OBJECT-TYPE
        SYNTAX      LacpPortEntry
        MAX-ACCESS  not-accessible
        STATUS      current
        DESCRIPTION "Entry for LACP port configuration. While an entry may
                     exist for a particular port, the port may not support
                     LACP and an attempt to enable LACP may result in
                     failure."
        INDEX       { lacpPortIndex }
        ::= { lacpPortTable 1 }

LacpPortEntry ::= SEQUENCE
{
    lacpPortIndex            Integer32,
    lacpPortStatus           EnabledStatus
}

lacpPortIndex OBJECT-TYPE
        SYNTAX      Integer32
        MAX-ACCESS  not-accessible
        STATUS      current
        DESCRIPTION "The port interface of the lacpPortTable. The interface
                     identified by a particular value of this index is the
                     same interface as identified by the same value of
                     ifIndex in the IF-MIB."
        ::= { lacpPortEntry 1 }

lacpPortStatus OBJECT-TYPE
        SYNTAX      EnabledStatus
        MAX-ACCESS  read-write
        STATUS      current
        DESCRIPTION "Whether 802.3ad LACP is enabled."
        ::= { lacpPortEntry 2 }

--
-- staMgt
--

-- Management for Spanning Tree Algorithm (STA).
-- This has variables not already defined in the implemented
-- standard MIB(s).

-- for 1d(STP) start
staSystemStatus OBJECT-TYPE
        SYNTAX      EnabledStatus
        MAX-ACCESS  read-write
        STATUS      current
        DESCRIPTION "Global spanning tree status.
                     (1) Spanning tree protocol is enabled.
                     (2) Spanning tree protocol is disabled."
        DEFVAL      { enabled }
        ::= { staMgt 1 }
-- for 1d(STP) end

staPortTable OBJECT-TYPE
        SYNTAX      SEQUENCE OF StaPortEntry
        MAX-ACCESS  not-accessible
        STATUS      current
        DESCRIPTION "The table manages port settings for Spanning Tree
                     Protocol 802.1d, 802.1w or 802.1s depending on the
                     value specified by staProtocolType."
        REFERENCE "IEEE 802.1d, IEEE 802.1w, IEEE 802.1s."
        ::= { staMgt 2 }

staPortEntry OBJECT-TYPE
        SYNTAX      StaPortEntry
        MAX-ACCESS  not-accessible
        STATUS      current
        DESCRIPTION "The conceptual entry of staPortTable."
        INDEX       { staPortIndex }
        ::= { staPortTable 1 }

StaPortEntry ::= SEQUENCE
{
    staPortIndex                Integer32,
-- for 1d(STP) start
    staPortFastForward          EnabledStatus,
-- for 1d(STP) end
-- for 1w(RSTP) start
    staPortProtocolMigration    TruthValue,
    staPortAdminEdgePort        TruthValue,
    staPortOperEdgePort         TruthValue,
    staPortAdminPointToPoint    INTEGER,
    staPortOperPointToPoint     TruthValue,
    staPortLongPathCost         Integer32,
    staPortSystemStatus         EnabledStatus,
    staPortLongAdminPathCost    Integer32,
    staPortLongOperPathCost     Integer32,
-- for 1w(RSTP) end
-- for BPDU flooding configuration
    staPortBpduFlooding         EnabledStatus,
    staPortRootGuardAdminStatus EnabledStatus,
    staPortRootGuardOperStatus  EnabledStatus,
    stpPortBpduGuard            EnabledStatus,
    staPortAutoEdgePort         EnabledStatus
}

staPortIndex OBJECT-TYPE
        SYNTAX      Integer32
        MAX-ACCESS  not-accessible
        STATUS      current
        DESCRIPTION "The port and the trunk (excluding trunk member ports)
                     interface of the staPortTable. The interface identified
                     by a particular value of this index is the same interface
                     as identified by the same value of dot1dStpPort in the
                     BRIDGE-MIB."
        ::= { staPortEntry 1 }

-- for 1d(STP) start
staPortFastForward OBJECT-TYPE
        SYNTAX      EnabledStatus
        MAX-ACCESS  read-write
        STATUS      current
        DESCRIPTION "Whether fast forwarding is enabled."
        ::= { staPortEntry 2 }
-- for 1d(STP) end

-- for 1w(RSTP) start
staPortProtocolMigration OBJECT-TYPE
    SYNTAX      TruthValue
    MAX-ACCESS  read-write
    STATUS      current
    DESCRIPTION
        "When operating in RSTP (version 2) mode, writing true(1)
         to this object forces this port to transmit RSTP BPDUs.
         Any other operation on this object has no effect and
         it always returns false(2) when read."
    REFERENCE
        "IEEE 802.1w clause 14.8.2.4, 17.18.10, 17.26"
    ::= { staPortEntry 3 }

staPortAdminEdgePort OBJECT-TYPE
    SYNTAX      TruthValue
    MAX-ACCESS  read-write
    STATUS      current
    DESCRIPTION
        "The administrative value of the edge port parameter.  A
         value of true(1) indicates that this port should be
         assumed as an edge-port and a value of false(2) indicates
         that this port should be assumed as a non-edge-port."
    REFERENCE
        "IEEE 802.1t clause 14.8.2, 18.3.3"
    ::= { staPortEntry 4 }

staPortOperEdgePort OBJECT-TYPE
    SYNTAX      TruthValue
    MAX-ACCESS  read-only
    STATUS      current
    DESCRIPTION
        "The operational value of the edge port parameter. The object is
         initialized to the value of staPortAdminEdgePort and is set false
         when a BPDU is received."
    REFERENCE
        "IEEE 802.1t clause 14.8.2, 18.3.4"
    ::= { staPortEntry 5 }

staPortAdminPointToPoint OBJECT-TYPE
    SYNTAX      INTEGER
                {
                    forceTrue(0),
                    forceFalse(1),
                    auto(2)
                }
    MAX-ACCESS  read-write
    STATUS      current
     DESCRIPTION
        "The administrative point-to-point status of the LAN segment
         attached to this port. A value of forceTrue(0) indicates that
         this port should always be treated as if it is connected to
         a point-to-point link. A value of forceFalse(1) indicates
         that this port should be treated as having a shared media
         connection. A value of auto(2) indicates that this port is
         considered to have a point-to-point link if it is an Aggregator
         and all of its members are aggregatable, or if the MAC entity
         is configured for full duplex operation, either through
         auto-negotiation or by management means."
   REFERENCE
       "IEEE 802.1w clause 6.4.3, 6.5, 14.8.2"
   ::= { staPortEntry 6 }

staPortOperPointToPoint OBJECT-TYPE
    SYNTAX      TruthValue
    MAX-ACCESS  read-only
    STATUS      current
    DESCRIPTION
        "The operational point-to-point status of the LAN segment
         attached to this port. This indicates whether a port is
         considered to have a point-to-point connection or not.
         The value is determined by management or by auto-detection,
         as described in the staPortAdminPointToPoint object."
    REFERENCE
        "IEEE 802.1w clause 6.4.3, 6.5, 14.8.2"
    ::= { staPortEntry 7 }

staPortLongPathCost OBJECT-TYPE
    SYNTAX      Integer32(1..200000000)
    MAX-ACCESS  read-write
    STATUS      current
    DESCRIPTION
          "The contribution of this port to the path cost (in 32
          bits value) of paths towards the spanning tree root which
          include this port.

          This object is used to configure the spanning tree port
          path cost in the 32-bit value range when the
          staPathCostMethod is long(2).

          If the staPathCostMethod is short(1), this mib object is not
          instantiated."
    ::= { staPortEntry 8 }

staPortSystemStatus OBJECT-TYPE
        SYNTAX      EnabledStatus
        MAX-ACCESS  read-write
        STATUS      current
        DESCRIPTION "Per-port spanning tree status.
                     (1) Spanning tree protocol is enabled.
                     (2) Spanning tree protocol is disabled."
        DEFVAL      { enabled }
        ::= { staPortEntry 9 }

staPortLongAdminPathCost OBJECT-TYPE
    SYNTAX      Integer32(0..200000000)
    MAX-ACCESS  read-write
    STATUS      current
    DESCRIPTION
          "The admin value of the RSTP path cost or MST external pathcost.
          The contribution of this port to the path cost (in 32
          bits value) of paths towards the spanning tree root which
          include this port.

          This object is used to configure the spanning tree port
          path cost in the 32-bit value range when the
          staPathCostMethod is long(2).

          If the staPathCostMethod is short(1), this mib object is not
          instantiated.

          Setting this to 0 means that the path cost is automatically
          determined. In this case, read staPortLongOperPathCost to get
          the oper value."
    ::= { staPortEntry 10 }

staPortLongOperPathCost OBJECT-TYPE
    SYNTAX      Integer32(1..200000000)
    MAX-ACCESS  read-only
    STATUS      current
    DESCRIPTION
          "The oper value of the RSTP path cost or MST external pathcost.
          The contribution of this port to the path cost (in 32
          bits value) of paths towards the spanning tree root which
          include this port.

          This object is used to configure the spanning tree port
          path cost in the 32-bit value range when the
          staPathCostMethod is long(2).

          If the staPathCostMethod is short(1), this mib object is not
          instantiated."
    ::= { staPortEntry 11 }

-- [ASE3528B-E1-FLF-P5-00008]
-- BPUD flooding can be configured per port when spanning tree is disable

staPortBpduFlooding     OBJECT-TYPE
    SYNTAX      EnabledStatus
    MAX-ACCESS  read-write
    STATUS      current
    DESCRIPTION "This parameter is used to configure the capability of BPDUs
                 flooding."
    ::= { staPortEntry 12 }

-- [ES4649-ZZ-01400]
-- Adding a new feature: XSTP Root Guard.

staPortRootGuardAdminStatus OBJECT-TYPE
    SYNTAX      EnabledStatus
    MAX-ACCESS  read-write
    STATUS      current
    DESCRIPTION "Specifies the desired status of the root guard. This variable configures the root
                 guard feature to enforce the root bridge placement in the network."
    ::= { staPortEntry 13 }

-- [ES4649-ZZ-01400]
-- Adding a new feature: XSTP Root Guard.

staPortRootGuardOperStatus OBJECT-TYPE
    SYNTAX      EnabledStatus
    MAX-ACCESS  read-only
    STATUS      current
    DESCRIPTION "The current operational status of the root guard which provides a
                 way to enforce the root bridge placement in the network.
    ::= { staPortEntry 14 }

-- [Juniper]
-- Not implement

stpPortBpduGuard         OBJECT-TYPE
    SYNTAX      EnabledStatus
    MAX-ACCESS  read-write
    STATUS      current
    DESCRIPTION "A value of enabled(1) indicates that BPDU port guard feature
                 is enabled for each port. A value of disabled(2) indicates
                 that the feature is disabled.
    ::= { staPortEntry 15 }

-- [Juniper]

staPortAutoEdgePort    OBJECT-TYPE
    SYNTAX      EnabledStatus
    MAX-ACCESS  read-write
    STATUS      current
    DESCRIPTION "Sets enabled(1) to enable the status of auto edge port which is
                 a feature defined in IEEE 802.1D-2004 17.25 and sets disabled(2) to
                 disable the status of auto edge port which is a feature defined
                 in IEEE 802.1D-2004 17.25. This feature automatically identifies an edge port
                 and makes dot1dStpPortOperEdgePort enabled."
    ::= { staPortEntry 16 }

staProtocolType OBJECT-TYPE
    SYNTAX      INTEGER {
                    stp(1),
                    rstp(2),
                    mstp(3)
                }
    MAX-ACCESS  read-write
    STATUS      current
    DESCRIPTION "The version of Spanning Tree Protocol the bridge is currently
                 running. The value 'stp(1)' indicates the Spanning Tree
                 Protocol is as specified in IEEE 802.1D,'rstp(2)' indicates that
                 the Rapid Spanning Tree Protocol is as specified in IEEE
                 802.1w, and the value 'mstp(3)' indicates that the Multiple Spanning
                 Tree Protocol is as specified in IEEE 802.1s. New values may
                 be defined in the future as new or updated versions of the
                 protocol become available."
    REFERENCE
        "IEEE 802.1w clause 14.8.1, 17.12, 17.16.1"
    ::= { staMgt 3 }


staTxHoldCount OBJECT-TYPE
    SYNTAX      Integer32 (1..10)
    MAX-ACCESS  read-write
    STATUS      current
    DESCRIPTION
        "The value used by the Port Transmit state machine to limit
         the maximum transmission rate."
    REFERENCE
        "IEEE 802.1w clause 17.16.6"
    DEFVAL      { 3 }
    ::= { staMgt 4 }

staPathCostMethod    OBJECT-TYPE
    SYNTAX       StaPathCostMode
    MAX-ACCESS   read-write
    STATUS       current
    DESCRIPTION "Indicates the type of spanning tree path cost mode configured
                 on the switch. This mode applies to all instances of the
                 spanning tree protocol running on the switch.

                 When the value of this MIB object is changed, the path cost of
                 all ports will be reassigned to the default path cost values
                 based on the new spanning tree path cost mode and the
                 ports' speed.

                 When the value of this MIB object is set to long(2), the
                 staPortLongPathCost MIB object must be used to retrieve/configure
                 the spanning tree port path cost as a 32-bit value.
                 The set operation on dot1dStpPortPathCost in BRIDGE-MIB will be rejected.
                 While retrieving the value of dot1dStpPortPathCost, the maximum
                 value of 65535 will be returned if the value of staPortLongPathCost
                 for the same instance exceeds 65535.

                 When the value of this MIB object is set to short(1), the
                 dot1dStpPortPathCost in BRIDGE-MIB must be used."
   DEFVAL  { short }
   ::= { staMgt 5}

staBridgePriorityDefault OBJECT-TYPE
    SYNTAX      INTEGER {
                    stp8021d1998(1),
                    stp8021t2001(2)
                }
    MAX-ACCESS  read-write
    STATUS      current
    DESCRIPTION
        "The version of the Spanning Tree default Bridge Priority
         that is to be used by this Bridge.

         stp8021d1998(1) - indicates the use of Bridge Priority
                           as defined in IEEE Std. 802.1D-1998.

         stp8021t2001(2) - indicates the use of Bridge Priority
                           as defined in IEEE Std. 802.1t."
    REFERENCE
        "IEEE 802.1D-1998 & IEEE 802.1t"
    ::= { staMgt  7 }

-- for 1w(RSTP) end

-- for 1s(MSTP) start
--
-- xstMgt
--

xstMgt OBJECT IDENTIFIER ::= { staMgt 6}

mstName OBJECT-TYPE
    SYNTAX      DisplayString(SIZE(0..32))
    MAX-ACCESS  read-write
    STATUS      current
    DESCRIPTION "The name of the Multiple Spanning Tree region."
    ::= { xstMgt 1 }

mstRevision OBJECT-TYPE
    SYNTAX      Integer32
    MAX-ACCESS  read-write
    STATUS      current
    DESCRIPTION "The Revision number of the Multiple Spanning Tree region."
    ::= { xstMgt 2 }

mstMaxHops OBJECT-TYPE
    SYNTAX      Integer32(1..40)
    MAX-ACCESS  read-write
    STATUS      current
    DESCRIPTION "The max hop number counts of the Multiple Spanning Tree region."
    ::= { xstMgt 3 }

xstInstanceCfgTable OBJECT-TYPE
    SYNTAX      SEQUENCE OF XstInstanceCfgEntry
    MAX-ACCESS  not-accessible
    STATUS      current
    DESCRIPTION "This table is used to configure the property of a specific
                 instance in Multiple Spanning Tree or Rapid Spanning Tree.
                 If Rapid Spanning Tree protocol is in use, the
                 mstInstanceEditIndex is always 0."
    ::= { xstMgt 4 }

xstInstanceCfgEntry OBJECT-TYPE
    SYNTAX      XstInstanceCfgEntry
    MAX-ACCESS  not-accessible
    STATUS      current
    DESCRIPTION "A conceptual row containing the property of the RST or MST instance."
    INDEX       { xstInstanceCfgIndex }
    ::= { xstInstanceCfgTable 1 }

XstInstanceCfgEntry ::= SEQUENCE
{
      xstInstanceCfgIndex                    Integer32,
      xstInstanceCfgPriority                 Integer32,
      xstInstanceCfgTimeSinceTopologyChange  TimeTicks,
      xstInstanceCfgTopChanges               Integer32,
      xstInstanceCfgDesignatedRoot           BridgeId,
      xstInstanceCfgRootCost                 Integer32,
      xstInstanceCfgRootPort                 Integer32,
      xstInstanceCfgMaxAge                   Timeout,
      xstInstanceCfgHelloTime                Timeout,
      xstInstanceCfgHoldTime                 Timeout,
      xstInstanceCfgForwardDelay             Timeout,
      xstInstanceCfgBridgeMaxAge             Timeout,
      xstInstanceCfgBridgeHelloTime          Timeout,
      xstInstanceCfgBridgeForwardDelay       Timeout,
      xstInstanceCfgTxHoldCount              Integer32,
      xstInstanceCfgPathCostMethod           StaPathCostMode
}

xstInstanceCfgIndex OBJECT-TYPE
      SYNTAX      Integer32 (0..4094)
      MAX-ACCESS  not-accessible
      STATUS      current
      DESCRIPTION
          "An arbitrary integer within the range from 1 to the value of
          the maximum instance that uniquely identifies a spanning
          tree instance."
      ::= {xstInstanceCfgEntry 1 }

xstInstanceCfgPriority OBJECT-TYPE
     SYNTAX      Integer32 (0..61440)
     MAX-ACCESS  read-write
     STATUS      current
     DESCRIPTION "The priority of a specific spanning tree instance.
                  The value assigned should be in the range 0-61440
                  in steps of 4096."
     ::= { xstInstanceCfgEntry 2 }


xstInstanceCfgTimeSinceTopologyChange OBJECT-TYPE
     SYNTAX      TimeTicks
     MAX-ACCESS  read-only
     STATUS      current
     DESCRIPTION "The time (in hundredths of a second) since the last topology
                 change detected by the bridge entity in RST or MST."
     ::= { xstInstanceCfgEntry 3 }

xstInstanceCfgTopChanges OBJECT-TYPE
     SYNTAX      Integer32
     MAX-ACCESS  read-only
     STATUS      current
     DESCRIPTION "The total number of topology changes detected by
                 this bridge in RST or MST since the management entity
                 was last reset or initialized."
     ::= { xstInstanceCfgEntry 4 }


xstInstanceCfgDesignatedRoot OBJECT-TYPE
     SYNTAX      BridgeId
     MAX-ACCESS  read-only
     STATUS      current
     DESCRIPTION "The bridge identifier of the root of the spanning
                 tree as determined by the Multiple Spanning Tree Protocol. (802.1s)
                 or Rapid Spanning Tree Protocol (802.1w) executed by this node.
                 This value is used as the root identifier parameter in
                 all configuration bridge PDUs originated by this node."
     REFERENCE   "IEEE 802.1w."
     ::= { xstInstanceCfgEntry 5 }

xstInstanceCfgRootCost OBJECT-TYPE
     SYNTAX      Integer32
     MAX-ACCESS  read-only
     STATUS      current
     DESCRIPTION "The cost of the path to the root as seen from
                 this bridge of the RST or MST."
     ::= { xstInstanceCfgEntry 6 }


xstInstanceCfgRootPort OBJECT-TYPE
     SYNTAX      Integer32
     MAX-ACCESS  read-only
     STATUS      current
     DESCRIPTION "The number of the port which offers the
                 lowest cost path from this bridge to the root
                 bridge of the RST or MST."
     ::= { xstInstanceCfgEntry 7 }

xstInstanceCfgMaxAge OBJECT-TYPE
     SYNTAX      Timeout
     MAX-ACCESS  read-only
     STATUS      current
     DESCRIPTION "The maximum age of Multiple Spanning Tree Protocol (802.1s)
                 or Rapid Spanning Tree Protocol (802.1w) information learned
                 from the network on any port before it is discarded,
                 in units of hundredths of a second. This is the actual
                 value that this bridge is currently using."
     ::= { xstInstanceCfgEntry 8 }


xstInstanceCfgHelloTime OBJECT-TYPE
     SYNTAX      Timeout
     MAX-ACCESS  read-only
     STATUS      current
     DESCRIPTION  "The amount of time between the transmission of
                  configuration bridge PDUs by this node on any port
                  when it is the root of the specific spanning tree or trying
                  to become so, in units of hundredths of a second.
                  This is the actual value that this bridge is
                  currently using in RST or MST."
     ::= { xstInstanceCfgEntry 9 }

xstInstanceCfgHoldTime OBJECT-TYPE
     SYNTAX      Timeout
     MAX-ACCESS  read-only
     STATUS      current
     DESCRIPTION  "This time value determines the interval length
                  during which no more than two configuration bridge
                  PDUs shall be transmitted by this node, in units
                  of hundredths of a second."
     ::= { xstInstanceCfgEntry 10 }

xstInstanceCfgForwardDelay OBJECT-TYPE
     SYNTAX      Timeout
     MAX-ACCESS  read-only
     STATUS      current
     DESCRIPTION  "For RST or MST protocol, this time value, measured in units of
                  hundredths of a second, controls how fast a port changes
                  its spanning state when moving towards the forwarding
                  state.  The value determines how long the port
                  stays in each of the listening and learning
                  states, which precede the forwarding state.  This
                  value is also used, when a topology change has
                  been detected and is underway, to age all dynamic
                  entries in the forwarding database. This value is the
                  current value being used by the bridge.
                  xstInstanceCfgBridgeForwardDelay defines the value that
                  this bridge and all others would start using
                  if/when this bridge were to become the root."
     ::= { xstInstanceCfgEntry 11 }

xstInstanceCfgBridgeMaxAge OBJECT-TYPE
     SYNTAX      Timeout
     MAX-ACCESS  read-only
     STATUS      current
     DESCRIPTION   "For RST or MST protocol, the time (in hundredths of second)
                   that all bridges use for MaxAge when this bridge is acting
                   as the root. Note that 802.1D-1990 specifies that the range
                   for this parameter is related to the value of
                   xstInstanceCfgBridgeHelloTime. The granularity of this
                   timer is specified by 802.1D-1990 to be 1 second."
     REFERENCE   "802.1D-1990."
     ::= { xstInstanceCfgEntry 12 }

xstInstanceCfgBridgeHelloTime OBJECT-TYPE
     SYNTAX      Timeout
     MAX-ACCESS  read-only
     STATUS      current
     DESCRIPTION   "For RST or MST protocol,the time (in hundredths of a second) that
                   all bridges use for HelloTime when this bridge is acting
                   as the root. The granularity of this timer is specified
                   by 802.1D-1990 to be 1 second."
     REFERENCE   "802.1D-1990."
     ::= { xstInstanceCfgEntry 13 }


xstInstanceCfgBridgeForwardDelay OBJECT-TYPE
     SYNTAX      Timeout
     MAX-ACCESS  read-only
     STATUS      current
     DESCRIPTION  "For RST or MST protocol, the time (in hundredths of a second)
                  that all bridges use for ForwardDelay when this bridge
                  is acting as the root.
                  Note that 802.1D-1990 specifies that the range for this
                  parameter is related to the value of
                  xstInstanceCfgBridgeMaxAge. The granularity of this
                  timer is specified by 802.1D-1990 to be 1 second."
     REFERENCE   "802.1D-1990."
     ::= { xstInstanceCfgEntry 14 }

xstInstanceCfgTxHoldCount OBJECT-TYPE
     SYNTAX      Integer32
     MAX-ACCESS  read-only
     STATUS      current
     DESCRIPTION  "For RST or MST protocol, the value used by the port transmit
                  state machine to limit the maximum transmission rate."
     ::= { xstInstanceCfgEntry 15 }

xstInstanceCfgPathCostMethod OBJECT-TYPE
     SYNTAX      StaPathCostMode
     MAX-ACCESS  read-only
     STATUS      current
     DESCRIPTION
       "For RST or MST protocol, this indicates the type of spanning tree path
       cost mode used by the switch. The mode applies to all instances of the
       Spanning Tree protocol running on the switch.

       When the value of this MIB object is changed, the path cost
       of all ports will be reassigned to the default path cost
       values based on the new spanning tree path cost mode and the
       ports' speed.

       When the value of this MIB object is set to long(2),
       the xstInstancePortPathCost MIB object must be used in order
       to retrieve/configure the spanning tree port path cost as a
       32-bit value. The set operation on dot1dStpPortPathCost in
       BRIDGE-MIB will be rejected. While retrieving the value of
       dot1dStpPortPathCost, the maximum value of 65535 will be
       returned if the value of xstInstancePortPathCost for the same
       instance exceeds 65535.

       When the value of this MIB object is set to short(1),
       the dot1dStpPortPathCost in BRIDGE-MIB must be used."
     ::= { xstInstanceCfgEntry 16 }

xstInstancePortTable OBJECT-TYPE
     SYNTAX      SEQUENCE OF XstInstancePortEntry
     MAX-ACCESS  not-accessible
     STATUS      current
     DESCRIPTION "The extension table for dot1dStpPortEntry to provide
                 additional Spanning Tree information and configuration."
     ::= { xstMgt 5 }

xstInstancePortEntry OBJECT-TYPE
     SYNTAX      XstInstancePortEntry
     MAX-ACCESS  not-accessible
     STATUS      current
     DESCRIPTION "The conceptual row for xstInstancePortTable."
     INDEX       { xstInstancePortInstance, xstInstancePortPort }
     ::= { xstInstancePortTable 1 }

XstInstancePortEntry ::= SEQUENCE
{
  xstInstancePortInstance           Integer32,
  xstInstancePortPort               Integer32,
  xstInstancePortPriority           Integer32,
  xstInstancePortState              INTEGER,
  xstInstancePortEnable             EnabledStatus,
  xstInstancePortPathCost           Integer32,
  xstInstancePortDesignatedRoot     BridgeId,
  xstInstancePortDesignatedCost     Integer32,
  xstInstancePortDesignatedBridge   BridgeId,
  xstInstancePortDesignatedPort     OCTET STRING,
  xstInstancePortForwardTransitions Counter32,
  xstInstancePortPortRole           INTEGER,
  xstInstancePortAdminPathCost      Integer32,
  xstInstancePortOperPathCost       Integer32
}

xstInstancePortInstance OBJECT-TYPE
     SYNTAX      Integer32
     MAX-ACCESS  not-accessible
     STATUS      current
     DESCRIPTION "The instance of the MSTP."
     ::= { xstInstancePortEntry 1 }

xstInstancePortPort OBJECT-TYPE
     SYNTAX      Integer32
     MAX-ACCESS  not-accessible
     STATUS      current
     DESCRIPTION "The port and the trunk (excluding trunk member ports)
                  interface of the mstInstancePortTable. The interface identified
                  by a particular value of this index is the same interface
                  as identified by the same value of dot1dStpPort in the BRIDGE-MIB."
     ::= { xstInstancePortEntry 2 }

xstInstancePortPriority OBJECT-TYPE
     SYNTAX      Integer32(0..240)
     MAX-ACCESS  read-write
     STATUS      current
     DESCRIPTION "Defines the priority used for this port in the Spanning
                 Tree Algorithm. If the path cost for all ports on a
                 switch is the same, the port with the highest priority
                 (i.e., lowest value) will be configured as an active link
                 in the Spanning Tree. This makes a port with higher
                 priority less likely to be blocked if the Spanning Tree
                 Algorithm is detecting network loops. Where more than one
                 port is assigned the highest priority, the port with
                 lowest numeric identifier will be enabled."
     ::= { xstInstancePortEntry 3 }

xstInstancePortState OBJECT-TYPE
     SYNTAX      INTEGER {
                          discarding(1),
                          learning(2),
                          forwarding(3)
                         }
     MAX-ACCESS  read-only
     STATUS  current
     DESCRIPTION  "The port's current state as defined by application of
                  the Spanning Tree Protocol.  This state controls what
                  action a port takes on reception of a frame:
                  discarding(1): Port receives configuration messages,
                                 but does not forward packets.
                  learning(2):   Port has transmitted configuration messages
                                 for an interval set by the Forward Delay
                                 parameter without receiving contradictory
                                 information. Port address table is cleared,
                                 and the port begins learning addresses.
                  forwarding(3): Port forwards packets, and continues learning
                                 addresses.

                  For ports which are disabled (see xstInstancePortEnable),
                  this object will have a value of discarding(1)."
              ::= { xstInstancePortEntry 4}

xstInstancePortEnable OBJECT-TYPE
     SYNTAX     EnabledStatus
     MAX-ACCESS  read-only
     STATUS      current
     DESCRIPTION    "The enabled/disabled status of the port."
     ::= { xstInstancePortEntry 5 }

xstInstancePortPathCost OBJECT-TYPE
     SYNTAX      Integer32(1..200000000)
     MAX-ACCESS  read-write
     STATUS      current
     DESCRIPTION "The pathcost of the RST or MST in the range 1 to 200000000.
                  This parameter is used to determine the best path between
                  devices. Therefore, lower values should be assigned to
                  ports attached to faster media, and higher values assigned
                  to ports with slower media. (Path cost takes precedence
                  over port priority)."
     ::= { xstInstancePortEntry 6 }

xstInstancePortDesignatedRoot OBJECT-TYPE
     SYNTAX      BridgeId
     MAX-ACCESS  read-only
     STATUS      current
     DESCRIPTION
                 "The unique bridge identifier of the bridge
                 recorded as the root in the configuration BPDUs
                 transmitted by the designated bridge for the
                 segment to which the port is attached."
     ::= { xstInstancePortEntry 7 }

xstInstancePortDesignatedCost OBJECT-TYPE
     SYNTAX      Integer32
     MAX-ACCESS  read-only
     STATUS      current
     DESCRIPTION
                 "The path cost of the designated port of the
                  segment connected to this port.  This value is
                  compared to the root path cost field in received
                  bridge PDUs."
     ::= { xstInstancePortEntry 8 }

xstInstancePortDesignatedBridge OBJECT-TYPE
     SYNTAX      BridgeId
     MAX-ACCESS  read-only
     STATUS      current
     DESCRIPTION
                 "The bridge identifier of the bridge which this
                 port considers to be the designated bridge for
                 this port's segment."
     ::= { xstInstancePortEntry 9 }

xstInstancePortDesignatedPort OBJECT-TYPE
     SYNTAX      OCTET STRING (SIZE (2))
     MAX-ACCESS  read-only
     STATUS      current
     DESCRIPTION
            "The port identifier of the port on the designated
            bridge for this port's segment."
     ::= { xstInstancePortEntry 10 }

xstInstancePortForwardTransitions OBJECT-TYPE
     SYNTAX  Counter32
     MAX-ACCESS  read-only
     STATUS  current
     DESCRIPTION
             "The number of times this port has transitioned
             from the learning state to the forwarding state."
     ::= { xstInstancePortEntry 11 }

xstInstancePortPortRole OBJECT-TYPE
     SYNTAX  INTEGER
             {
               disabled(1),
               root(2),
               designated(3),
               alternate(4),
               backup(5),
               master(6)
             }
     MAX-ACCESS read-only
     STATUS current
     DESCRIPTION "The role of the port in the RST or MST protocol:
                  (1) The port has no role within the spanning tree
                  (2) The port is part of the active topology connecting
                      the bridge to the root bridge (i.e., root port)
                  (3) The port is connecting a LAN through the bridge to the
                      root bridge (i.e., designated port)
                  (4) The port may provide connectivity if other
                      bridges, bridge ports, or LANs fail or are removed.
                  (5) The port provides backup if other
                      bridges, bridge ports, or LANs fail or are removed.
                  (6) For MST protocol only, indicates whether this instance
                      is in a master role."
     ::= { xstInstancePortEntry 12 }

xstInstancePortAdminPathCost OBJECT-TYPE
     SYNTAX      Integer32(1..200000000)
     MAX-ACCESS  read-write
     STATUS      current
     DESCRIPTION "The admin value of the RST pathcost or MST internal pathcost,
                  in the range of 1 to 200000000.
                  This parameter is used to determine the best path between
                  devices. Therefore, lower values should be assigned to
                  ports attached to faster media, and higher values assigned
                  to ports with slower media. (Path cost takes precedence
                  over port priority)."
     ::= { xstInstancePortEntry 13 }

xstInstancePortOperPathCost OBJECT-TYPE
     SYNTAX      Integer32(1..200000000)
     MAX-ACCESS  read-only
     STATUS      current
     DESCRIPTION "The oper value of the RST pathcost or MST internal pathcost,
                  in the range of 1 to 200000000.
                  This parameter is used to determine the best path between
                  devices. Therefore, lower values should be assigned to
                  ports attached to faster media, and higher values assigned
                  to ports with slower media. (Path cost takes precedence
                  over port priority)."
     ::= { xstInstancePortEntry 14 }

mstInstanceEditTable OBJECT-TYPE
     SYNTAX      SEQUENCE OF MstInstanceEditEntry
     MAX-ACCESS  not-accessible
     STATUS      current
     DESCRIPTION "The Multiple Spanning Tree region instance vlan configuration table.
                  Please read the actual instance vlan mapped in the mstInstanceOperTable."
     ::= { xstMgt 6 }

mstInstanceEditEntry OBJECT-TYPE
     SYNTAX      MstInstanceEditEntry
     MAX-ACCESS  not-accessible
     STATUS      current
     DESCRIPTION  "A conceptual row containing the status of the MSTP instance."
     INDEX       { mstInstanceEditIndex }
     ::= { mstInstanceEditTable 1 }

MstInstanceEditEntry ::= SEQUENCE
{
    mstInstanceEditIndex      Integer32,
    mstInstanceEditVlansMap   OCTET STRING,
    mstInstanceEditVlansMap2k OCTET STRING,
    mstInstanceEditVlansMap3k OCTET STRING,
    mstInstanceEditVlansMap4k OCTET STRING,
    mstInstanceEditRemainingHops Integer32
}

mstInstanceEditIndex OBJECT-TYPE
      SYNTAX      Integer32 (0..4094)
      MAX-ACCESS  not-accessible
      STATUS      current
      DESCRIPTION
          "An arbitrary integer within the range from 1 to the value of
          the maximum instance that uniquely identifies a spanning
          tree instance."
      ::= {mstInstanceEditEntry 1 }

mstInstanceEditVlansMap OBJECT-TYPE
    SYNTAX     OCTET STRING (SIZE (0..128))
    MAX-ACCESS read-create
    STATUS     current
    DESCRIPTION
            "A string of octets containing one bit per VLAN. The
            first octet corresponds to VLANs with vlanIndex values
            of 0 through 7; the second octet to VLANs 8 through
            15; etc., The most significant bit of each octet
            corresponds to the lowest value vlanIndex in that octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 2 }

mstInstanceEditVlansMap2k OBJECT-TYPE
    SYNTAX     OCTET STRING (SIZE (0..128))
    MAX-ACCESS read-create
    STATUS     current
    DESCRIPTION
            "A string of octets containing one bit per VLAN for
            VLANS with vlanIndex values of 1024 through 2047. The
            first octet corresponds to VLANs with vlanIndex values
            of 1024 through 1031; the second octet to VLANs 1032
            through 1039; etc. The most significant bit of each
            octet corresponds to the lowest value vlanIndex in that
            octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 3 }

mstInstanceEditVlansMap3k OBJECT-TYPE
    SYNTAX     OCTET STRING (SIZE (0..128))
    MAX-ACCESS read-create
    STATUS     current
    DESCRIPTION
            "A string of octets containing one bit per VLAN for
            VLANS with vlanIndex values of 2048 through 3071. The
            first octet corresponds to VLANs with vlanIndex values
            of 2048 through 2055; the second octet to VLANs 2056
            through 2063; etc. The most significant bit of each
            octet corresponds to the lowest value vlanIndex in that
            octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 4 }

mstInstanceEditVlansMap4k OBJECT-TYPE
    SYNTAX     OCTET STRING (SIZE (0..128))
    MAX-ACCESS read-create
    STATUS     current
    DESCRIPTION
            "A string of octets containing one bit per VLAN for
            VLANS with vlanIndex values of 3072 through 4095. The
            first octet corresponds to VLANs with vlanIndex values
            of 3072 through 3079; the second octet to VLANs 3080
            through 3087; etc. The most significant bit of each
            octet corresponds to the lowest value vlanIndex in that
            octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 5 }

mstInstanceEditRemainingHops OBJECT-TYPE
     SYNTAX      Integer32
     MAX-ACCESS  read-only
     STATUS      current
     DESCRIPTION "The remaining hop count for this MST instance."
     ::= { mstInstanceEditEntry 6 }

--mstInstanceOperTable
mstInstanceOperTable OBJECT-TYPE
     SYNTAX      SEQUENCE OF MstInstanceOperEntry
     MAX-ACCESS  not-accessible
     STATUS      current
     DESCRIPTION "The Multiple Spanning Tree region instance vlan mapped table."
     ::= { xstMgt 7 }

mstInstanceOperEntry OBJECT-TYPE
     SYNTAX      MstInstanceOperEntry
     MAX-ACCESS  not-accessible
     STATUS      current
     DESCRIPTION  "A conceptual row containing the status of the MSTP instance."
     INDEX       { mstInstanceOperIndex }
     ::= { mstInstanceOperTable 1 }

MstInstanceOperEntry ::= SEQUENCE
{
    mstInstanceOperIndex      Integer32,
    mstInstanceOperVlansMap   OCTET STRING,
    mstInstanceOperVlansMap2k OCTET STRING,
    mstInstanceOperVlansMap3k OCTET STRING,
    mstInstanceOperVlansMap4k OCTET STRING
}

mstInstanceOperIndex OBJECT-TYPE
      SYNTAX      Integer32 (0..4094)
      MAX-ACCESS  not-accessible
      STATUS      current
      DESCRIPTION
          "An arbitrary integer within the range from 1 to the value of
          the maximum instance that uniquely identifies a spanning
          tree instance."
      ::= {mstInstanceOperEntry 1 }

mstInstanceOperVlansMap OBJECT-TYPE
    SYNTAX     OCTET STRING (SIZE (0..128))
    MAX-ACCESS read-only
    STATUS     current
    DESCRIPTION
            "A string of octets containing one bit per VLAN. The
            first octet corresponds to VLANs with vlanIndex values
            of 0 through 7; the second octet to VLANs 8 through
            15; etc., The most significant bit of each octet
            corresponds to the lowest value vlanIndex in that octet.

            For each VLAN, if it is mapped to this MSTP instance,
            then the bit corresponding to that VLAN is set to '1'."
    ::= {mstInstanceOperEntry 2 }

mstInstanceOperVlansMap2k OBJECT-TYPE
    SYNTAX     OCTET STRING (SIZE (0..128))
    MAX-ACCESS read-only
    STATUS     current
    DESCRIPTION
            "A string of octets containing one bit per VLAN for
            VLANS with vlanIndex values of 1024 through 2047. The
            first octet corresponds to VLANs with vlanIndex values
            of 1024 through 1031; the second octet to VLANs 1032
            through 1039; etc. The most significant bit of each
            octet corresponds to the lowest value vlanIndex in that
            octet.

            For each VLAN, if it is mapped to this MSTP instance,
            then the bit corresponding to that VLAN is set to '1'."
    ::= {mstInstanceOperEntry 3 }

mstInstanceOperVlansMap3k OBJECT-TYPE
    SYNTAX     OCTET STRING (SIZE (0..128))
    MAX-ACCESS read-only
    STATUS     current
    DESCRIPTION
            "A string of octets containing one bit per VLAN for
            VLANS with vlanIndex values of 2048 through 3071. The
            first octet corresponds to VLANs with vlanIndex values
            of 2048 through 2055; the second octet to VLANs 2056
            through 2063; etc. The most significant bit of each
            octet corresponds to the lowest value vlanIndex in that
            octet.

            For each VLAN, if it is mapped to this MSTP instance,
            then the bit corresponding to that VLAN is set to '1'."
    ::= {mstInstanceOperEntry 4 }

mstInstanceOperVlansMap4k OBJECT-TYPE
    SYNTAX     OCTET STRING (SIZE (0..128))
    MAX-ACCESS read-only
    STATUS     current
    DESCRIPTION
            "A string of octets containing one bit per VLAN for
            VLANS with vlanIndex values of 3072 through 4095. The
            first octet corresponds to VLANs with vlanIndex values
            of 3072 through 3079; the second octet to VLANs 3080
            through 3087; etc. The most significant bit of each
            octet corresponds to the lowest value vlanIndex in that
            octet.

            For each VLAN, if it is mapped to this MSTP instance,
            then the bit corresponding to that VLAN is set to '1'."
    ::= {mstInstanceOperEntry 5 }

-- for 1s(MSTP) end
--
-- tftpMgt
--

-- Management for Trivial File Transfer Protocol (TFTP).
-- This is responsible for file upload to a server and download
-- from a server.


tftpFileType  OBJECT-TYPE
    SYNTAX     INTEGER {
                  opcode(1),
                  config(2)
               }
    MAX-ACCESS read-write
    STATUS     current
    DESCRIPTION
        "Type of file to transfer."
    ::= { tftpMgt 1 }

tftpSrcFile  OBJECT-TYPE
    SYNTAX     DisplayString (SIZE(0..127))
    MAX-ACCESS read-write
    STATUS     current
    DESCRIPTION
        "The source file name for TFTP transfer when a
        transfer is next requested via this MIB. This value is set to
        the zero length string when no file name has been specified."
    ::= { tftpMgt 2 }

tftpDestFile  OBJECT-TYPE
    SYNTAX     DisplayString (SIZE(0..127))
    MAX-ACCESS read-write
    STATUS     current
    DESCRIPTION
        "The destination file name for TFTP transfer when a
        transfer is next requested via this MIB. This value is set to
        the zero length string when no file name has been specified."
    ::= { tftpMgt 3 }

tftpServer  OBJECT-TYPE
    SYNTAX     IpAddress
    MAX-ACCESS read-write
    STATUS     current
    DESCRIPTION
        "The IP address of the TFTP server for transfer
        when a download is next requested via this MIB.
        This value is set to '0.0.0.0' when no IP address has been
        specified."
    ::= { tftpMgt 4 }

tftpAction  OBJECT-TYPE
    SYNTAX     INTEGER {
                  notDownloading(1),
                  downloadToPROM(2),
                  downloadToRAM(3),
                  upload(4)
               }
    MAX-ACCESS read-write
    STATUS     current
    DESCRIPTION
        "When the device is not downloading, this object will have
        a value of notDownloading(1).

        When this object is set to downloadToPROM(2),
        the device will discontinue its
        normal operation and begin download of the file specified
        by tftpSrcFile from the server specified by
        tftpServer to tftpDestFile in the device
        using the TFTP protocol. This action is the same as
        the CLI command 'copy tftp file'.

        Currently downloadToRAM(3) is not supported

        When this object is set to upload(4), the device will begin
        upload of the file specified by tftpScrFile in the device
        to tftpDestFile in the server specified by tftpServer.
        This action is the same as the CLI command 'copy file tftp'."
     REFERENCE
        " RMON2-MIB, mib2(1).rmon(16).probeConfig(19).probeDownloadAction(8)."
    ::= { tftpMgt 5 }

tftpStatus  OBJECT-TYPE
    SYNTAX     INTEGER {
                    tftpSuccess(1),
                    tftpStatusUnknown(2),
                    tftpGeneralError(3),
                    tftpNoResponseFromServer(4),
                    tftpDownloadChecksumError(5),--download only
                    tftpDownloadIncompatibleImage(6),--download only
                    tftpTftpFileNotFound(7),
                    tftpTftpAccessViolation(8)
               }
    MAX-ACCESS read-only
    STATUS     current
    DESCRIPTION
        "The status of the last transfer procedure, if any. This
        object will have a value of downloadStatusUnknown(2) if no
        transfer process has been performed."
    ::= { tftpMgt 6 }


--
-- restartMgt
--

-- Management for restarting the switch.


restartOpCodeFile OBJECT-TYPE
        SYNTAX      DisplayString (SIZE(0..32))
        MAX-ACCESS  read-write
        STATUS      current
        DESCRIPTION "Name of op-code file for start-up."
        ::= { restartMgt 1 }

restartConfigFile OBJECT-TYPE
        SYNTAX      DisplayString (SIZE(0..32))
        MAX-ACCESS  read-write
        STATUS      current
        DESCRIPTION "Name of configuration file for start-up."
        ::= { restartMgt 2 }

restartControl  OBJECT-TYPE
    SYNTAX     INTEGER {
                    running(1),
                    warmBoot(2),
                    coldBoot(3)
              }
    MAX-ACCESS read-write
    STATUS     current
    DESCRIPTION
        "Setting this object to warmBoot(2) causes the device to
         reinitialize itself such that neither the agent configuration
         nor the protocol entity implementation is altered. Setting this
         object to coldBoot(3) causes the device to reinitialize itself such
         that the agent's configuration or the protocol entity implementation
         may be altered. When the device is running normally, this
         variable has a value of running(1)."
    ::= { restartMgt 3 }


restartResetMgt OBJECT IDENTIFIER ::= { restartMgt 4 }

restartResetBlade OBJECT-TYPE
     SYNTAX      INTEGER
                 {
                   noReset(1),
                   reset(2)
                 }
     MAX-ACCESS  read-write
     STATUS      current
     DESCRIPTION "This variables is used to reset the specific blade in the
                  FTTH system, Set to Reset(2) to reset the blade number
                  specific in bladeIndex. noReset(1) will always be obtained
                  when reading this variable."
     ::= { restartResetMgt 1 }

restartResetBladePort OBJECT-TYPE
      SYNTAX      Integer32
      MAX-ACCESS  read-write
      STATUS      current
      DESCRIPTION "Set the value of port number to reset the port.
                   0 will always be obtained when reading this variable."
      ::= { restartResetMgt 2 }

--
-- mirrorMgt
--

-- Management for port mirroring.

mirrorTable OBJECT-TYPE
        SYNTAX      SEQUENCE OF MirrorEntry
        MAX-ACCESS  not-accessible
        STATUS      current
        DESCRIPTION "Table for port mirroring, enabling a port to be mirrored
                     to/from another port. Not all ports can be mirrored and
                     limitations may apply as to which ports can be used as either
                     source or destination ports."
        ::= { mirrorMgt 1 }

mirrorEntry OBJECT-TYPE
        SYNTAX      MirrorEntry
        MAX-ACCESS  not-accessible
        STATUS      current
        DESCRIPTION "The conceptual row of mirrorTable."
        INDEX       { mirrorDestinationPort, mirrorSourcePort }
        ::= { mirrorTable 1 }

MirrorEntry ::= SEQUENCE
{
    mirrorDestinationPort  Integer32,
    mirrorSourcePort       Integer32,
    mirrorType             INTEGER,
    mirrorStatus           ValidStatus
}

mirrorDestinationPort OBJECT-TYPE
        SYNTAX      Integer32
        MAX-ACCESS  not-accessible
        STATUS      current
        DESCRIPTION "The destination port interface for mirrored packets.
                     The interface identified by a particular value of
                     this index is the same interface as identified by
                     the same value of ifIndex in the IF-MIB."
        ::= { mirrorEntry 1 }

mirrorSourcePort OBJECT-TYPE
        SYNTAX      Integer32
        MAX-ACCESS  not-accessible
        STATUS      current
        DESCRIPTION "The source port interface for mirrored packets.
                     The interface identified by a particular value of
                     this index is the same interface as identified by
                     the same value of ifIndex in the IF-MIB."
        ::= { mirrorEntry 2 }

mirrorType OBJECT-TYPE
        SYNTAX      INTEGER
                    {
                        rx(1),
                        tx(2),
                        both(3)
                    }
        MAX-ACCESS  read-create
        STATUS      current
        DESCRIPTION "If this value is rx(1), receive packets will
                    be mirrored. If this value is tx(2), transmit
                    packets will be mirrored. If this value is both(3),
                    both receive and transmit packets will be mirrored."
        ::= { mirrorEntry 3 }

mirrorStatus OBJECT-TYPE
        SYNTAX      ValidStatus
        MAX-ACCESS  read-create
        STATUS      current
        DESCRIPTION "Setting this to valid(1) creates an entry.
                     Setting this to invalid(2) destroys an entry."
        ::= { mirrorEntry 4 }

--
-- igmpSnoopMgt
--

-- Management for Internet Group Management Protocol (IGMP)
-- Snooping.


igmpSnoopStatus OBJECT-TYPE
        SYNTAX      EnabledStatus
        MAX-ACCESS  read-write
        STATUS      current
        DESCRIPTION "Parameter to enable or disable IGMP snooping on the device.
                     When enabled, the device will examine IGMP packets and set
                     up filters for IGMP ports. "
        DEFVAL      { enabled }
        ::= { igmpSnoopMgt 1 }

igmpSnoopQuerier OBJECT-TYPE
        SYNTAX      EnabledStatus
        MAX-ACCESS  read-write
        STATUS      current
        DESCRIPTION "Enables (disables) whether the switch acts as an IGMP
                     querier."
        DEFVAL      { enabled }
        ::= { igmpSnoopMgt 2 }

igmpSnoopQueryCount OBJECT-TYPE
        SYNTAX      Integer32 (2..10)
        MAX-ACCESS  read-write
        STATUS      current
        DESCRIPTION "The query count from a querier, during which a response is
                     expected from an endstation. If a querier has sent a
                     number of counts defined by igmpSnoopQueryCount, but an
                     endstation has not responded, a countdown timer is
                     started using the time defined by igmpSnoopQueryMaxResponseTime.
                     If the countdown finishes, and the endstation still has
                     not responded, then that endstation is deemed to have left
                     the multicast group."
        DEFVAL      { 2 }
        ::= { igmpSnoopMgt 3 }


igmpSnoopQueryInterval OBJECT-TYPE
        SYNTAX      Integer32 (60..125)
        MAX-ACCESS  read-write
        STATUS      current
        DESCRIPTION "The interval (in seconds) between IGMP host-query
                     messages sent by the switch."
        DEFVAL      { 125 }
        ::= { igmpSnoopMgt 4 }

igmpSnoopQueryMaxResponseTime OBJECT-TYPE
        SYNTAX      Integer32 (5..25)
        MAX-ACCESS  read-write
        STATUS      current
        DESCRIPTION "The time after a query, during which a response is
                     expected from an endstation. If a querier has sent
                     a number of queries defined by igmpSnoopQueryCount,
                     but an endstation has not responded, a countdown
                     timer is started using an initial value set by
                     igmpSnoopQueryMaxResponseTime. If the countdown
                     finishes, and the endstation still has not responded,
                     then that the endstation is deemed to have
                     left the multicast group."
        DEFVAL      { 10 }
        ::= { igmpSnoopMgt 5 }

igmpSnoopRouterPortExpireTime OBJECT-TYPE
        SYNTAX      Integer32 (300..500)
        MAX-ACCESS  read-write
        STATUS      current
        DESCRIPTION "Sets the time (in seconds) the switch waits after
                     the previous querier has stopped querying before
                     the router port (which received query packets from
                     previous querier) expires."
        DEFVAL      { 300 }
        ::= { igmpSnoopMgt 6 }

igmpSnoopVersion OBJECT-TYPE
        SYNTAX      Integer32 (1..3)
        MAX-ACCESS  read-write
        STATUS      current
        DESCRIPTION "IGMP version snooped"
        DEFVAL      { 2 }
        ::= { igmpSnoopMgt 7 }

igmpSnoopRouterCurrentTable OBJECT-TYPE
    SYNTAX      SEQUENCE OF IgmpSnoopRouterCurrentEntry
    MAX-ACCESS  not-accessible
    STATUS      current
    DESCRIPTION
        "Table for current router ports."
    ::= { igmpSnoopMgt 8 }

igmpSnoopRouterCurrentEntry OBJECT-TYPE
    SYNTAX      IgmpSnoopRouterCurrentEntry
    MAX-ACCESS  not-accessible
    STATUS      current
    DESCRIPTION
        "Entry for current router ports."
    INDEX   { igmpSnoopRouterCurrentVlanIndex }
    ::= {
igmpSnoopRouterCurrentTable 1 }

IgmpSnoopRouterCurrentEntry ::=
    SEQUENCE {
        igmpSnoopRouterCurrentVlanIndex
            Unsigned32,
        igmpSnoopRouterCurrentPorts
            PortList,
        igmpSnoopRouterCurrentStatus
            PortList
    }

igmpSnoopRouterCurrentVlanIndex OBJECT-TYPE
    SYNTAX      Unsigned32
    MAX-ACCESS  not-accessible
    STATUS      current
    DESCRIPTION
        "The interface identified by a particular value of
         this index is the same interface as identified by
         the same value of dot1qVlanIndex in the Q-BRIDGE-MIB.
         The entry will only appear here after a configure to
         igmpSnoopRouterStaticTable."
    ::= { igmpSnoopRouterCurrentEntry 1 }

igmpSnoopRouterCurrentPorts OBJECT-TYPE
    SYNTAX      PortList
    MAX-ACCESS  read-only
    STATUS      current
    DESCRIPTION "The set of ports which are current router ports, including static
                 router ports. Please refer to igmpSnoopRouterStaticTable."
    ::= { igmpSnoopRouterCurrentEntry 2 }

igmpSnoopRouterCurrentStatus OBJECT-TYPE
    SYNTAX      PortList
    MAX-ACCESS  read-only
    STATUS      current
    DESCRIPTION
        "The set of ports which are static multicast router ports."
    ::= { igmpSnoopRouterCurrentEntry 3 }

igmpSnoopRouterStaticTable OBJECT-TYPE
    SYNTAX      SEQUENCE OF IgmpSnoopRouterStaticEntry
    MAX-ACCESS  not-accessible
    STATUS      current
    DESCRIPTION
        "Table for static router ports."
    ::= { igmpSnoopMgt 9 }

-- [Juniper]

igmpSnoopUnknownDataForward      OBJECT-TYPE
    SYNTAX      INTEGER
                {
                    flood(1),
                    toRouterPorts(2)
                }
    MAX-ACCESS  read-write
    STATUS      current
    DESCRIPTION "Specifies the processing mode for unknown multicast data packets.
                 A value of flood(1) indicates that the unknown multicast data packets
                 are flooded to all ports. A value of toRouterPort(2) means that the
                 unknown multicast data packets are forwarded to router ports."
    ::= { igmpSnoopMgt 26 }

igmpSnoopRouterStaticEntry OBJECT-TYPE
    SYNTAX      IgmpSnoopRouterStaticEntry
    MAX-ACCESS  not-accessible
    STATUS      current
    DESCRIPTION
        "Entry for static router ports."
    INDEX   { igmpSnoopRouterStaticVlanIndex }
    ::= {
igmpSnoopRouterStaticTable 1 }

IgmpSnoopRouterStaticEntry ::=
    SEQUENCE {
        igmpSnoopRouterStaticVlanIndex
            Unsigned32,
        igmpSnoopRouterStaticPorts
            PortList,
        igmpSnoopRouterStaticStatus
            ValidStatus
    }

igmpSnoopRouterStaticVlanIndex OBJECT-TYPE
    SYNTAX      Unsigned32
    MAX-ACCESS  not-accessible
    STATUS      current
    DESCRIPTION
        "The interface identified by a particular value of
         this index is the same interface as identified by
         the same value of dot1qVlanIndex in the Q-BRIDGE-MIB.
         The entry will only appear here after a configure to
         igmpSnoopRouterStaticTable."
    ::= { igmpSnoopRouterStaticEntry 1 }

igmpSnoopRouterStaticPorts OBJECT-TYPE
    SYNTAX      PortList
    MAX-ACCESS  read-create
    STATUS      current
    DESCRIPTION
        "The set of ports which are static router ports."
    ::= { igmpSnoopRouterStaticEntry 2 }

igmpSnoopRouterStaticStatus OBJECT-TYPE
    SYNTAX      ValidStatus
    MAX-ACCESS  read-create
    STATUS      current
    DESCRIPTION
        "Setting this to valid(1) creates an entry.
         Setting this to invalid(2) destroys an entry."
    ::= { igmpSnoopRouterStaticEntry 3 }

igmpSnoopMulticastCurrentTable OBJECT-TYPE
    SYNTAX      SEQUENCE OF IgmpSnoopMulticastCurrentEntry
    MAX-ACCESS  not-accessible
    STATUS      current
    DESCRIPTION
        "Table for current multicast addresses."
    ::= { igmpSnoopMgt 10 }

igmpSnoopMulticastCurrentEntry OBJECT-TYPE
    SYNTAX      IgmpSnoopMulticastCurrentEntry
    MAX-ACCESS  not-accessible
    STATUS      current
    DESCRIPTION
        "Entry for current multicast addresses."
    INDEX   { igmpSnoopMulticastCurrentVlanIndex,
              igmpSnoopMulticastCurrentIpAddress }
    ::= {
igmpSnoopMulticastCurrentTable 1 }

IgmpSnoopMulticastCurrentEntry ::=
    SEQUENCE {
        igmpSnoopMulticastCurrentVlanIndex
            Unsigned32,
        igmpSnoopMulticastCurrentIpAddress
            IpAddress,
        igmpSnoopMulticastCurrentPorts
            PortList,
        igmpSnoopMulticastCurrentStatus
            PortList
    }

igmpSnoopMulticastCurrentVlanIndex OBJECT-TYPE
    SYNTAX      Unsigned32
    MAX-ACCESS  not-accessible
    STATUS      current
    DESCRIPTION
        "The interface identified by a particular value of
         this index is the same interface as identified by
         the same value of dot1qVlanIndex in the Q-BRIDGE-MIB.
         The entry will only appear here after a configure to
         igmpSnoopMulticastStaticTable."
    ::= { igmpSnoopMulticastCurrentEntry 1 }

igmpSnoopMulticastCurrentIpAddress OBJECT-TYPE
    SYNTAX      IpAddress
    MAX-ACCESS  not-accessible
    STATUS      current
    DESCRIPTION
        "IP address of multicast group."
    ::= { igmpSnoopMulticastCurrentEntry 2 }

igmpSnoopMulticastCurrentPorts OBJECT-TYPE
    SYNTAX      PortList
    MAX-ACCESS  read-only
    STATUS      current
    DESCRIPTION
        "The set of ports which are members of a multicast group, including
         static members. Please refer to igmpSnoopMulticastStaticTable."
    ::= { igmpSnoopMulticastCurrentEntry 3 }

igmpSnoopMulticastCurrentStatus OBJECT-TYPE
    SYNTAX      PortList
    MAX-ACCESS  read-only
    STATUS      current
    DESCRIPTION
        "The set of ports which are static IGMP member ports."
    ::= { igmpSnoopMulticastCurrentEntry 4 }

igmpSnoopMulticastStaticTable OBJECT-TYPE
    SYNTAX      SEQUENCE OF IgmpSnoopMulticastStaticEntry
    MAX-ACCESS  not-accessible
    STATUS      current
    DESCRIPTION
        "Table for static multicast addresses."
    ::= { igmpSnoopMgt 11 }

igmpSnoopMulticastStaticEntry OBJECT-TYPE
    SYNTAX      IgmpSnoopMulticastStaticEntry
    MAX-ACCESS  not-accessible
    STATUS      current
    DESCRIPTION
        "Entry for static multicast addresses."
    INDEX   { igmpSnoopMulticastStaticVlanIndex,
              igmpSnoopMulticastStaticIpAddress }
    ::= {
igmpSnoopMulticastStaticTable 1 }

IgmpSnoopMulticastStaticEntry ::=
    SEQUENCE {
        igmpSnoopMulticastStaticVlanIndex
            Unsigned32,
        igmpSnoopMulticastStaticIpAddress
            IpAddress,
        igmpSnoopMulticastStaticPorts
            PortList,
        igmpSnoopMulticastStaticStatus
            ValidStatus
    }

igmpSnoopMulticastStaticVlanIndex OBJECT-TYPE
    SYNTAX      Unsigned32
    MAX-ACCESS  not-accessible
    STATUS      current
    DESCRIPTION
        "The interface identified by a particular value of
         this index is the same interface as identified by
         the same value of dot1qVlanIndex in the Q-BRIDGE-MIB.
         The entry will only appear here after a configure to
         igmpSnoopMulticastStaticTable."
    ::= { igmpSnoopMulticastStaticEntry 1 }

igmpSnoopMulticastStaticIpAddress OBJECT-TYPE
    SYNTAX      IpAddress
    MAX-ACCESS  not-accessible
    STATUS      current
    DESCRIPTION
        "IP address of multicast group."
    ::= { igmpSnoopMulticastStaticEntry 2 }

igmpSnoopMulticastStaticPorts OBJECT-TYPE
    SYNTAX      PortList
    MAX-ACCESS  read-create
    STATUS      current
    DESCRIPTION
        "The set of ports which are members."
    ::= { igmpSnoopMulticastStaticEntry 3 }

igmpSnoopMulticastStaticStatus OBJECT-TYPE
    SYNTAX      ValidStatus
    MAX-ACCESS  read-create
    STATUS      current
    DESCRIPTION
        "Setting this to valid(1) creates an entry.
         Setting this to invalid(2) destroys an entry."
    ::= { igmpSnoopMulticastStaticEntry 4 }

igmpSnoopSystemRouterCurrentPorts OBJECT-TYPE
    SYNTAX      PortList
    MAX-ACCESS  read-only
    STATUS      current
    DESCRIPTION
        "The set of ports which are current router ports,
         including static router ports. Please refer to
         igmpSnoopSystemRouterStaticPorts."
    ::= {igmpSnoopMgt 12}

igmpSnoopSystemRouterStaticPorts OBJECT-TYPE
    SYNTAX      PortList
    MAX-ACCESS  read-write
    STATUS      current
    DESCRIPTION
        "The set of ports which are static router ports."
    ::= {igmpSnoopMgt 13}

igmpSnoopCurrentVlanTable OBJECT-TYPE
        SYNTAX      SEQUENCE OF IgmpSnoopCurrentVlanEntry
        MAX-ACCESS  not-accessible
        STATUS      current
        DESCRIPTION "Table for configuring IGMP snooping for each VLAN
                     which exists in the device by (local or network)
                     management, or dynamically created as a result of
                     GVRP requests received."
        ::= { igmpSnoopMgt 14 }

igmpSnoopCurrentVlanEntry OBJECT-TYPE
        SYNTAX      IgmpSnoopCurrentVlanEntry
        MAX-ACCESS  not-accessible
        STATUS      current
        DESCRIPTION "Entry for configuring IGMP snooping."
        INDEX       { igmpSnoopCurrentVlanIndex }
        ::= { igmpSnoopCurrentVlanTable 1 }

IgmpSnoopCurrentVlanEntry ::= SEQUENCE
{
    igmpSnoopCurrentVlanIndex     Unsigned32,
    igmpSnoopCurrentVlanEnable    EnabledStatus,
    igmpSnoopCurrentVlanImmediateLeave    EnabledStatus
}

igmpSnoopCurrentVlanIndex OBJECT-TYPE
        SYNTAX      Unsigned32
        MAX-ACCESS  not-accessible
        STATUS      current
        DESCRIPTION "Same is dot1qVlanIndex in the Q-BRIDGE-MIB.
            This table has only one entry - the entry for
            the VLAN of the management interface."
        ::= { igmpSnoopCurrentVlanEntry 1 }

igmpSnoopCurrentVlanEnable OBJECT-TYPE
        SYNTAX      EnabledStatus
        MAX-ACCESS  read-write
        STATUS      current
        DESCRIPTION "Parameter to enable or disable IGMP snooping on this VLAN.
                     When enabled, the device will examine IGMP packets and set
                     up filters for IGMP ports."
        ::= { igmpSnoopCurrentVlanEntry 2 }

igmpSnoopCurrentVlanImmediateLeave OBJECT-TYPE
        SYNTAX      EnabledStatus
        MAX-ACCESS  read-write
        STATUS      current
        DESCRIPTION "The parameter to enable or disable the Immediate-Leave feature on this VLAN."
        ::= { igmpSnoopCurrentVlanEntry 3 }

igmpSnoopLeaveProxy OBJECT-TYPE
        SYNTAX      EnabledStatus
        MAX-ACCESS  read-write
        STATUS      current
        DESCRIPTION "The parameter to enable or disable the IGMP Leave Proxy."
        ::= { igmpSnoopMgt 15 }

igmpSnoopReportSuppressionStatus OBJECT-TYPE
    SYNTAX      EnabledStatus
    MAX-ACCESS  read-write
    STATUS      deprecated
    DESCRIPTION
        "Parameter to enable or disable IGMP snooping report suppression on the device.
        When enabled, the device will suppress superabundance report and leave packets.
        Only the First copy of Report Packet or the Last copy of Leave Packet for the
        same Group will be forwarded to route ports.
        Status changed to deprecated:this function is always enable."
    DEFVAL      { enabled }
    ::= { igmpSnoopMgt 16 }

igmpSnoopFilterStatus OBJECT-TYPE
    SYNTAX      EnabledStatus
    MAX-ACCESS  read-write
    STATUS      current
    DESCRIPTION
        "Parameter to enable or disable IGMP filtering on the device."
    ::= { igmpSnoopMgt 17 }

igmpSnoopProfileTable OBJECT-TYPE
        SYNTAX      SEQUENCE OF IgmpSnoopProfileEntry
        MAX-ACCESS  not-accessible
        STATUS      current
        DESCRIPTION "The table for configuring the IGMP snooping profile."
        ::= { igmpSnoopMgt 18 }

igmpSnoopProfileEntry OBJECT-TYPE
        SYNTAX      IgmpSnoopProfileEntry
        MAX-ACCESS  not-accessible
        STATUS      current
        DESCRIPTION "The entry for configuring the IGMP snooping profile."
        INDEX       { igmpSnoopProfileId }
        ::= { igmpSnoopProfileTable 1 }

IgmpSnoopProfileEntry ::= SEQUENCE
{
    igmpSnoopProfileId               Unsigned32,
    igmpSnoopProfileAction           INTEGER,
    igmpSnoopProfileStatus           ValidStatus
}

igmpSnoopProfileId OBJECT-TYPE
        SYNTAX      Unsigned32
        MAX-ACCESS  not-accessible
        STATUS      current
        DESCRIPTION "The ID of the IGMP snooping profile."
        ::= { igmpSnoopProfileEntry 1 }

igmpSnoopProfileAction OBJECT-TYPE
    SYNTAX      INTEGER
                {
                    permit(1),
                    deny(2)
                }
    MAX-ACCESS  read-write
    STATUS      current
    DESCRIPTION "The access mode of the IGMP snooping profile."
    DEFVAL      { deny }
    ::= { igmpSnoopProfileEntry 2 }

igmpSnoopProfileStatus OBJECT-TYPE
        SYNTAX      ValidStatus
        MAX-ACCESS  read-write
        STATUS      current
        DESCRIPTION "Setting this to valid(1) creates an entry.
                     Setting this to invalid(2) destroys an entry."
        ::= { igmpSnoopProfileEntry 3 }

igmpSnoopProfileCtl      OBJECT IDENTIFIER   ::= { igmpSnoopMgt 19 }

igmpSnoopProfileCtlId   OBJECT-TYPE
        SYNTAX      Unsigned32
        MAX-ACCESS  read-write
        STATUS      current
        DESCRIPTION "The ID of the IGMP snooping profile."
        ::= { igmpSnoopProfileCtl 1 }

igmpSnoopProfileCtlInetAddressType OBJECT-TYPE
    SYNTAX      InetAddressType
    MAX-ACCESS  read-write
    STATUS      current
    DESCRIPTION
      "The address type is associated with this agent.
       Only ipv4(1) type is supported."
    ::= { igmpSnoopProfileCtl 2 }

igmpSnoopProfileCtlStartInetAddress OBJECT-TYPE
        SYNTAX      InetAddress
        MAX-ACCESS  read-write
        STATUS      current
        DESCRIPTION "The specified addresses in the start of the controlled IP multicast addresses."
        ::= { igmpSnoopProfileCtl 3 }

igmpSnoopProfileCtlEndInetAddress OBJECT-TYPE
        SYNTAX      InetAddress
        MAX-ACCESS  read-write
        STATUS      current
        DESCRIPTION "The specified addresses in the end of the controlled IP multicast addresses."
        ::= { igmpSnoopProfileCtl 4 }

igmpSnoopProfileCtlAction   OBJECT-TYPE
        SYNTAX      INTEGER
        {
            noAction(1),
            create(2),
            destroy(3)
        }
        MAX-ACCESS  read-write
        STATUS      current
        DESCRIPTION "Setting it to create(2) creates the range of the controlled IP multicast addresses.
                     Setting it to destroy(3) destroys the range of the controlled IP multicast addresses.
                     When the action is completed, this object becomes noAction(1)."
        ::= { igmpSnoopProfileCtl 5 }

igmpSnoopProfileRangeTable OBJECT-TYPE
        SYNTAX      SEQUENCE OF IgmpSnoopProfileRangeEntry
        MAX-ACCESS  not-accessible
        STATUS      current
        DESCRIPTION "The table for configuring the range of the IGMP snooping profile."
        ::= { igmpSnoopMgt 20 }

igmpSnoopProfileRangeEntry OBJECT-TYPE
        SYNTAX      IgmpSnoopProfileRangeEntry
        MAX-ACCESS  not-accessible
        STATUS      current
        DESCRIPTION "The entry for configuring the range of the IGMP snooping profile."
        INDEX       { igmpSnoopProfileRangeProfileId ,igmpSnoopProfileRangeInetAddressType,igmpSnoopProfileRangeStartInetAddress }
        ::= { igmpSnoopProfileRangeTable 1 }

IgmpSnoopProfileRangeEntry ::= SEQUENCE
{
    igmpSnoopProfileRangeProfileId           Unsigned32,
    igmpSnoopProfileRangeInetAddressType     InetAddressType,
    igmpSnoopProfileRangeStartInetAddress    InetAddress,
    igmpSnoopProfileRangeEndInetAddress      InetAddress,
    igmpSnoopProfileRangeAction              INTEGER
}

igmpSnoopProfileRangeProfileId  OBJECT-TYPE
        SYNTAX      Unsigned32
        MAX-ACCESS  not-accessible
        STATUS      current
        DESCRIPTION "This is defined as igmpSnoopProfileId."
        ::= { igmpSnoopProfileRangeEntry 1 }

igmpSnoopProfileRangeInetAddressType OBJECT-TYPE
    SYNTAX      InetAddressType
    MAX-ACCESS  not-accessible
    STATUS      current
    DESCRIPTION
      "The address type is associated with this agent.
        Only ipv4(1) type is supported."
    ::= { igmpSnoopProfileRangeEntry 2 }

igmpSnoopProfileRangeStartInetAddress OBJECT-TYPE
        SYNTAX      InetAddress
        MAX-ACCESS  not-accessible
        STATUS      current
        DESCRIPTION "The specified addresses in the start of the controlled IP multicast addresses."
        ::= { igmpSnoopProfileRangeEntry 3 }

igmpSnoopProfileRangeEndInetAddress OBJECT-TYPE
        SYNTAX      InetAddress
        MAX-ACCESS  read-only
        STATUS      current
        DESCRIPTION "The specified addresses in the end of the controlled IP multicast addresses."
        ::= { igmpSnoopProfileRangeEntry 4 }

igmpSnoopProfileRangeAction OBJECT-TYPE
    SYNTAX      INTEGER
                {
                    permit(1),
                    deny(2)
                }
    MAX-ACCESS  read-only
    STATUS      current
    DESCRIPTION "The access mode of the IGMP snooping profile."
    DEFVAL      { deny }
    ::= { igmpSnoopProfileRangeEntry 5 }

igmpSnoopFilterPortTable OBJECT-TYPE
        SYNTAX      SEQUENCE OF IgmpSnoopFilterPortEntry
        MAX-ACCESS  not-accessible
        STATUS      current
        DESCRIPTION "Table for port configuration in IGMP filtering."
        ::= { igmpSnoopMgt 21 }

igmpSnoopFilterPortEntry OBJECT-TYPE
        SYNTAX      IgmpSnoopFilterPortEntry
        MAX-ACCESS  not-accessible
        STATUS      current
        DESCRIPTION "Entry for port configuration in IGMP filtering."
        INDEX       { igmpSnoopFilterPortIndex }
        ::= { igmpSnoopFilterPortTable 1 }

IgmpSnoopFilterPortEntry ::= SEQUENCE
{
    igmpSnoopFilterPortIndex              Unsigned32,
    igmpSnoopFilterPortProfileId          Integer32
}

igmpSnoopFilterPortIndex OBJECT-TYPE
        SYNTAX      Unsigned32
        MAX-ACCESS  not-accessible
        STATUS      current
        DESCRIPTION "The port and trunk (including trunk members) interface of
                     the portTable. The interface identified by a particular value
                     of this index is the same interface identified by the same
                     value of ifIndex in the IF-MIB."
        ::= { igmpSnoopFilterPortEntry 1 }

igmpSnoopFilterPortProfileId OBJECT-TYPE
        SYNTAX     Integer32
        MAX-ACCESS read-write
        STATUS     current
        DESCRIPTION
            "The igmpSnoopProfileEntry identified by a particular value of this index
             is the same interface identified by the same value of the igmpSnoopProfileId
             object. If there is no corresponding entry in the igmpSnoopProfileTable,
             then no association exists. In particular, if this value is zero, no
             associated profile will be generated, as zero is not a valid profile index."
        ::= { igmpSnoopFilterPortEntry 2 }

igmpSnoopThrottlePortTable OBJECT-TYPE
        SYNTAX      SEQUENCE OF IgmpSnoopThrottlePortEntry
        MAX-ACCESS  not-accessible
        STATUS      current
        DESCRIPTION "Table for port configuration in IGMP throttling."
        ::= { igmpSnoopMgt 22 }

igmpSnoopThrottlePortEntry OBJECT-TYPE
        SYNTAX      IgmpSnoopThrottlePortEntry
        MAX-ACCESS  not-accessible
        STATUS      current
        DESCRIPTION "Entry for port configuration in IGMP throttling."
        INDEX       { igmpSnoopThrottlePortIndex }
        ::= { igmpSnoopThrottlePortTable 1 }

IgmpSnoopThrottlePortEntry ::= SEQUENCE
{
    igmpSnoopThrottlePortIndex            Unsigned32,
    igmpSnoopThrottlePortRunningStatus    TruthValue,
    igmpSnoopThrottlePortAction           INTEGER,
    igmpSnoopThrottlePortMaxGroups        Integer32,
    igmpSnoopThrottlePortCurrentGroups    Integer32
}

igmpSnoopThrottlePortIndex OBJECT-TYPE
        SYNTAX      Unsigned32
        MAX-ACCESS  not-accessible
        STATUS      current
        DESCRIPTION "The port and trunk (including trunk members) interface of
                     the portTable. The interface identified by a particular value
                     of this index is the same interface identified by the same
                     value of ifIndex in the IF-MIB."
        ::= { igmpSnoopThrottlePortEntry 1 }

igmpSnoopThrottlePortRunningStatus OBJECT-TYPE
        SYNTAX  TruthValue
        MAX-ACCESS  read-only
        STATUS      current
        DESCRIPTION "Describes the running status of the IGMP throttling to the switch.
                     A value of true(1) indicates the IGMP throttling mechanism is active.
                     A value of false(2) indicates the IGMP throttling mechanism is inactive."
        ::= { igmpSnoopThrottlePortEntry 2 }

igmpSnoopThrottlePortAction OBJECT-TYPE
    SYNTAX      INTEGER
                {
                    replace(1),
                    deny(2)
                }
    MAX-ACCESS  read-write
    STATUS      current
    DESCRIPTION "The action mode of the IGMP throttling. A value of replace(1)
                 means to replace a joined multicast group randomly when an interface
                 receives an IGMP report and the number of current joined multicast groups
                 is equal to the maximum number of IGMP groups that the interface can join.
                 A value of deny(2) means to deny the IGMP report request when an interface
                 receives an IGMP report and the number of current joined multicast groups
                 is equal to the maximum number of IGMP groups that the interface can join."
    DEFVAL      { deny }
    ::= { igmpSnoopThrottlePortEntry 3 }

igmpSnoopThrottlePortMaxGroups  OBJECT-TYPE
        SYNTAX      Integer32(0..256)
        MAX-ACCESS  read-write
        STATUS      current
        DESCRIPTION "The maximum number of IGMP groups that the interface can join."
        ::= { igmpSnoopThrottlePortEntry 4 }

igmpSnoopThrottlePortCurrentGroups   OBJECT-TYPE
        SYNTAX      Integer32
        MAX-ACCESS  read-only
        STATUS      current
        DESCRIPTION "The current number of IGMP groups that the interface has joined."
        ::= { igmpSnoopThrottlePortEntry 5}

--
-- The IpMgt Group
--

-- Management for Internet Protocol (IP).

netConfigTable  OBJECT-TYPE
    SYNTAX     SEQUENCE OF NetConfigEntry
    MAX-ACCESS not-accessible
    STATUS     current
    DESCRIPTION
        "A table of netConfigEntry."
    ::= { ipMgt 1 }

netConfigEntry  OBJECT-TYPE
    SYNTAX     NetConfigEntry
    MAX-ACCESS not-accessible
    STATUS     current
    DESCRIPTION
        "A set of configuration parameters for a particular
        network interface on this device. If the device has no network
        interface, this table is empty.

        The index is composed of the ifIndex assigned to the
        corresponding interface."
    INDEX  { netConfigIfIndex, netConfigIPAddress, netConfigSubnetMask }
    ::= { netConfigTable 1 }

NetConfigEntry ::= SEQUENCE {
    netConfigIfIndex           Integer32,
    netConfigIPAddress         IpAddress,
    netConfigSubnetMask        IpAddress,
    netConfigPrimaryInterface  INTEGER,
    netConfigUnnumbered        INTEGER,
    netConfigStatus            RowStatus
}

netConfigIfIndex  OBJECT-TYPE
    SYNTAX     Integer32
    MAX-ACCESS not-accessible
    STATUS     current
    DESCRIPTION "The VLAN interface being used by this table entry. Only the
                 VLAN interfaces which have an IP configured will appear in
                 the table."
    ::= { netConfigEntry 1 }

netConfigIPAddress  OBJECT-TYPE
    SYNTAX     IpAddress
    MAX-ACCESS not-accessible
    STATUS     current
    DESCRIPTION
        "The IP address of this Net interface. The default value
        for this object is 0.0.0.0. If either the netConfigIPAddress
        or netConfigSubnetMask is 0.0.0.0, then when the device
        boots, it may use BOOTP to try to figure out what these
        values should be. If BOOTP fails, before the device
        can talk on the network, this value must be configured
        (e.g., through a terminal attached to the device)."
    ::= { netConfigEntry 2 }

netConfigSubnetMask  OBJECT-TYPE
    SYNTAX     IpAddress
    MAX-ACCESS not-accessible
    STATUS     current
    DESCRIPTION
        "The subnet mask of this Net interface. The default value
        for this object is 0.0.0.0. If either the netConfigIPAddress
        or netConfigSubnetMask are 0.0.0.0, then when the device
        boots, it may use BOOTP to try to figure out what these
        values should be. If BOOTP fails, before the device
        can talk on the network, this value must be configured
        (e.g., through a terminal attached to the device)."
    ::= { netConfigEntry 3 }

netConfigPrimaryInterface OBJECT-TYPE
    SYNTAX     INTEGER
               {
                   primary(1),
                   secondary(2)
               }
    MAX-ACCESS read-create
    STATUS     current
    DESCRIPTION
        "Whether this is a primary interface."
    ::= { netConfigEntry 4 }

netConfigUnnumbered OBJECT-TYPE
    SYNTAX     INTEGER
               {
                   unnumbered(1),
                   notUnnumbered(2)
               }
    MAX-ACCESS read-create
    STATUS     current
    DESCRIPTION
        "Whether this is an unnumbered interface."
    ::= { netConfigEntry 5 }

netConfigStatus  OBJECT-TYPE
    SYNTAX     RowStatus
    MAX-ACCESS read-create
    STATUS     current
    DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation: 'notReady', 'notInService' or
            'active'. That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { netConfigEntry 6 }

netDefaultGateway  OBJECT-TYPE
    SYNTAX     IpAddress
    MAX-ACCESS read-write
    STATUS     current
    DESCRIPTION
        "The IP Address of the default gateway. If this value is
        undefined or unknown, it shall have the value 0.0.0.0."
    ::= { ipMgt 2 }

ipHttpState OBJECT-TYPE
    SYNTAX     EnabledStatus
    MAX-ACCESS read-write
    STATUS     current
    DESCRIPTION
        "Whether HTTP is enabled."
    ::= { ipMgt 3 }

ipHttpPort OBJECT-TYPE
    SYNTAX     Integer32 (1..65535)
    MAX-ACCESS read-write
    STATUS     current
    DESCRIPTION
        "The port number for HTTP."
    ::= { ipMgt 4 }

ipDhcpRestart OBJECT-TYPE
    SYNTAX     INTEGER
               {
                   restart(1),
                   noRestart(2)
               }
    MAX-ACCESS read-write
    STATUS     current
    DESCRIPTION "When set to restart(1) the DHCP server will restart. When read,
                 this value always returns noRestart(2)."
    ::= { ipMgt 5 }

-- optional
ipHttpsState OBJECT-TYPE
    SYNTAX     EnabledStatus
    MAX-ACCESS read-write
    STATUS     current
    DESCRIPTION
        "Whether HTTPS is enabled."
    ::= { ipMgt 6 }

ipHttpsPort OBJECT-TYPE
    SYNTAX     Integer32 (1..65535)
    MAX-ACCESS read-write
    STATUS     current
    DESCRIPTION
        "The port number for HTTPS."
    ::= { ipMgt 7 }

-- for layer3
ipIcmpRedirectStatus OBJECT-TYPE
        SYNTAX      EnabledStatus
        MAX-ACCESS  read-write
        STATUS      current
        DESCRIPTION "Enable or disable ICMP redirect function."
        ::= { ipMgt 8 }

--
--ipInterfaceTable
--

ipInterfaceTable  OBJECT-TYPE
    SYNTAX     SEQUENCE OF IpInterfaceEntry
    MAX-ACCESS not-accessible
    STATUS     current
    DESCRIPTION
        "The ipInterface Table."
    ::= { ipMgt 9 }

ipInterfaceEntry  OBJECT-TYPE
    SYNTAX     IpInterfaceEntry
    MAX-ACCESS not-accessible
    STATUS     current
    DESCRIPTION
        "A set of configuration parameters for a particular
        network interface on this device. If the device has no network
        interface, this table is empty."
    INDEX  { ipInterfaceIPAddress, ipInterfaceSubnetMask }
    ::= { ipInterfaceTable 1 }

IpInterfaceEntry ::= SEQUENCE {
    ipInterfaceIPAddress        IpAddress,
    ipInterfaceSubnetMask       IpAddress,
    ipInterfaceIfIndex          Integer32,
    ipInterfacePrimaryInterface INTEGER,
    ipInterfaceStatus           RowStatus
}

ipInterfaceIPAddress  OBJECT-TYPE
    SYNTAX     IpAddress
    MAX-ACCESS not-accessible
    STATUS     current
    DESCRIPTION
        "The IP address of this Net interface. The default value
        for this object is 0.0.0.0. If either the ipInterfaceIPAddress
        or ipInterfaceSubnetMask is 0.0.0.0, then when the device
        boots, it may use BOOTP to try to figure out what these
        values should be. If BOOTP fails, before the device
        can talk on the network, this value must be configured
        (e.g., through a terminal attached to the device)."
    ::= { ipInterfaceEntry 1 }

ipInterfaceSubnetMask    OBJECT-TYPE
    SYNTAX     IpAddress
    MAX-ACCESS not-accessible
    STATUS     current
    DESCRIPTION
        "The subnet mask of this Net interface. The default value
        for this object is 0.0.0.0. If either the ipInterfaceIPAddress
        or ipInterfaceSubnetMask are 0.0.0.0, then when the device
        boots, it may use BOOTP to try to figure out what these
        values should be. If BOOTP fails, before the device
        can talk on the network, this value must be configured
        (e.g., through a terminal attached to the device)."
    ::= { ipInterfaceEntry 2 }

ipInterfaceIfIndex  OBJECT-TYPE
    SYNTAX      Integer32
    MAX-ACCESS  read-create
    STATUS      current
    DESCRIPTION "The VLAN interface being used by this table entry.
                 The interface identified by a particular value of this index is the
                 same interface as identified by the same value of
                 ifIndex in the IF-MIB."
    ::= { ipInterfaceEntry 3 }

ipInterfacePrimaryInterface  OBJECT-TYPE
    SYNTAX     INTEGER
               {
                   primary(1),
                   secondary(2)
               }
    MAX-ACCESS read-create
    STATUS     current
    DESCRIPTION
        "Whether this is a primary interface."
    ::= { ipInterfaceEntry 4 }

ipInterfaceStatus  OBJECT-TYPE
    SYNTAX     RowStatus
    MAX-ACCESS read-create
    STATUS     current
    DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation: 'notReady', 'notInService' or
            'active'. That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { ipInterfaceEntry 5 }


netIfMgt              OBJECT IDENTIFIER ::= { ipMgt 10 }

nifInterfaceTable OBJECT-TYPE
        SYNTAX      SEQUENCE OF NifInterfaceTable
        MAX-ACCESS  not-accessible
        STATUS      current
        DESCRIPTION "Table for network interface information listed by interface.
                     Depending on the nature of the product, this table may have
                     only one entry (e.g., for the management VLAN), or may have
                     many entries (e.g., for all ports, or for all static VLANs)."
        ::= { netIfMgt 1 }

nifInterfaceEntry OBJECT-TYPE
        SYNTAX      NifInterfaceTable
        MAX-ACCESS  not-accessible
        STATUS      current
        DESCRIPTION "Entry for network interface information listed by interface."
        INDEX       { nifInterfaceIndex }
        ::= { nifInterfaceTable 1 }

NifInterfaceTable ::= SEQUENCE
{
      nifInterfaceIndex           Integer32,
      nifInterfaceAddressMethod   INTEGER
}

nifInterfaceIndex OBJECT-TYPE
        SYNTAX      Integer32
        MAX-ACCESS  not-accessible
        STATUS      current
        DESCRIPTION "This is defined by ifIndex in the IF-MIB (vlan ifindex)."
        ::= { nifInterfaceEntry 1 }

nifInterfaceAddressMethod OBJECT-TYPE
        SYNTAX      INTEGER
                    {
                        user(1),
                        bootp(2),
                        dhcp(3)
                    }
        MAX-ACCESS  read-write
        STATUS      current
        DESCRIPTION "Method to get the IP Address."
        ::= { nifInterfaceEntry 2 }

dhcpMgt              OBJECT IDENTIFIER ::= { ipMgt 11 }
dhcpClient           OBJECT IDENTIFIER ::= { dhcpMgt 1 }
dhcpcOptions         OBJECT IDENTIFIER ::= { dhcpClient 1 }

dhcpcInterfaceTable OBJECT-TYPE
        SYNTAX      SEQUENCE OF DhcpcInterfaceTable
        MAX-ACCESS  not-accessible
        STATUS      current
        DESCRIPTION "Table for DHCP client information listed by interface.
                     Depending on the nature of the product, this table may
                     have only one entry(e.g., for the management VLAN), or
                     may have many entries(e.g., for all ports, or for all
                     static VLANs)."
        ::= { dhcpcOptions 1 }

dhcpcInterfaceEntry OBJECT-TYPE
        SYNTAX      DhcpcInterfaceTable
        MAX-ACCESS  not-accessible
        STATUS      current
        DESCRIPTION "Entry for DHCP client information listed by interface."
        INDEX       { dhcpcIfIndex }
        ::= { dhcpcInterfaceTable 1 }

DhcpcInterfaceTable ::= SEQUENCE
{
   dhcpcIfIndex         Integer32,
   dhcpcIfClientIdMode  INTEGER,
   dhcpcIfClientId      OCTET STRING
}

dhcpcIfIndex OBJECT-TYPE
        SYNTAX      Integer32
        MAX-ACCESS  not-accessible
        STATUS      current
        DESCRIPTION "This is defined by ifIndex in the IF-MIB (static vlan if index)."
        ::= { dhcpcInterfaceEntry 1 }

dhcpcIfClientIdMode OBJECT-TYPE
        SYNTAX      INTEGER
                    {
                      notSpecify(1),
                      text(2),
                      hex(3)
                    }
        MAX-ACCESS  read-write
        STATUS      current
        DESCRIPTION "Whether the client ID is in text mode or in hex mode."
        ::= { dhcpcInterfaceEntry 2 }

dhcpcIfClientId OBJECT-TYPE
         SYNTAX      OCTET STRING (SIZE(0..32))
         MAX-ACCESS  read-write
         STATUS      current
         DESCRIPTION "The value that the DHCP client sets in the client_id
                      option of DHCPDISCOVER and DHCPREQUEST messages. This
                      value may be used by DHCP servers to uniquely identify
                      the client."
         ::= { dhcpcInterfaceEntry 3 }

dhcpRelay OBJECT IDENTIFIER ::= { dhcpMgt 2 }

-- JBOS only
dhcpRelayIfTable OBJECT-TYPE
          SYNTAX      SEQUENCE OF DhcpRelayIfEntry
          MAX-ACCESS  not-accessible
          STATUS      current
          DESCRIPTION "The table to record the status of dhcpRelay."
          ::= { dhcpRelay 1 }

dhcpRelayIfEntry OBJECT-TYPE
          SYNTAX      DhcpRelayIfEntry
          MAX-ACCESS  not-accessible
          STATUS      current
          DESCRIPTION "A conceptual row of dhcpRelayIfTable."
          INDEX { dhcpRelayIfIndex }
          ::= { dhcpRelayIfTable 1 }

DhcpRelayIfEntry ::= SEQUENCE
{
     dhcpRelayIfIndex  Integer32,
     dhcpRelayIfStatus EnabledStatus
}

dhcpRelayIfIndex OBJECT-TYPE
          SYNTAX      Integer32
          MAX-ACCESS  not-accessible
          STATUS      current
          DESCRIPTION "VLAN interface on which this entry is defined."
          ::= { dhcpRelayIfEntry 1 }

dhcpRelayIfStatus OBJECT-TYPE
          SYNTAX      EnabledStatus
          MAX-ACCESS  read-write
          STATUS      current
          DESCRIPTION "The status of the dhcpRelay. Set this variable to enabled(1)
                       to enable dhcpRelay. Set this variable to disabled(2) to
                       disable dhcpRelay."
          ::= { dhcpRelayIfEntry 2 }

--dhcpRelayServerAddrTable
dhcpRelayServerAddrTable OBJECT-TYPE
          SYNTAX      SEQUENCE OF DhcpRelayServerAddrEntry
          MAX-ACCESS  not-accessible
          STATUS      current
          DESCRIPTION "The role of the DHCP relay agent is to forward requests
                        and replies between server and client when they are not
                        in the same subnet. To enable DHCP relay service the user needs to
                        specify relay server IP address and then restart DHCP relay.
                        This table is to specify relay server IP address,
                        the maximum number of server IP addresses user can specify is 5.
                        To restart DHCP relay, please use the dhcpRelayRestart variable."
          ::= { dhcpRelay 2 }

dhcpRelayServerAddrEntry OBJECT-TYPE
          SYNTAX      DhcpRelayServerAddrEntry
          MAX-ACCESS  not-accessible
          STATUS      current
          DESCRIPTION "A conceptual row of dhcpRelayServerAddrTable."
          INDEX { dhcpRelayServerAddrIfIndex,dhcpRelayServerAddrIndex }
          ::= { dhcpRelayServerAddrTable 1 }

DhcpRelayServerAddrEntry ::= SEQUENCE
{
     dhcpRelayServerAddrIfIndex  Integer32,
     dhcpRelayServerAddrIndex Integer32,
     dhcpRelayServerAddrServerIp  IpAddress
}

dhcpRelayServerAddrIfIndex OBJECT-TYPE
          SYNTAX      Integer32
          MAX-ACCESS  not-accessible
          STATUS      current
          DESCRIPTION "The VLAN interface being used by this table entry."
          ::= { dhcpRelayServerAddrEntry 1 }

dhcpRelayServerAddrIndex OBJECT-TYPE
          SYNTAX      Integer32 (0..5)
          MAX-ACCESS  not-accessible
          STATUS      current
          DESCRIPTION "The index of the relay server IP address."
          ::= { dhcpRelayServerAddrEntry 2 }

dhcpRelayServerAddrServerIp OBJECT-TYPE
          SYNTAX      IpAddress
          MAX-ACCESS  read-write
          STATUS      current
          DESCRIPTION "The IP address of the relay server."
          ::= { dhcpRelayServerAddrEntry 3 }

--dhcpRelayRestart
dhcpRelayRestart OBJECT-TYPE
          SYNTAX      INTEGER
                      {
                        restart(1),
                        noRestart(2)
                      }
          MAX-ACCESS  read-write
          STATUS      current
          DESCRIPTION "Set this object to restart(1) to restart DCHP Relay.
                       Always get noRestart(2) when you read this variable."
          ::= { dhcpRelay 3 }

--
-- dhcpServerMgt
--
dhcpServerMgt OBJECT IDENTIFIER ::= { dhcpMgt 3 }

--dhcpPoolTable
dhcpPoolTable OBJECT-TYPE
          SYNTAX      SEQUENCE OF DhcpPoolEntry
          MAX-ACCESS  not-accessible
          STATUS      current
          DESCRIPTION "A DHCP pool is a collection of
                       user configurations such as option config-lease time
                       or DNS server IPs, a network address for network pool,
                       or a host IP plus a hardware address pair for host pool.
                       However, a DHCP pool only can either be a network pool
                       or a host pool, or neither (such as that pool only
                       containing option config no network address config
                       or a host IP config as well)"
          ::= { dhcpServerMgt 1 }

dhcpPoolEntry OBJECT-TYPE
          SYNTAX      DhcpPoolEntry
          MAX-ACCESS  not-accessible
          STATUS      current
          DESCRIPTION "A conceptual row of dhcpPoolTable."
          INDEX { dhcpPoolPoolName }
          ::= { dhcpPoolTable 1 }

DhcpPoolEntry ::= SEQUENCE
{
     dhcpPoolPoolName  DisplayString,
     dhcpPoolPoolType INTEGER,
     dhcpPoolPoolAddress  IpAddress,
     dhcpPoolSubnetMask IpAddress,
     dhcpPoolHardwareType INTEGER,
     dhcpPoolMacAddress OCTET STRING,
     dhcpPoolstatus ValidStatus
}

dhcpPoolPoolName OBJECT-TYPE
          SYNTAX      DisplayString(SIZE(1..8))
          MAX-ACCESS  not-accessible
          STATUS      current
          DESCRIPTION "PoolName; simply specify a string with
                      string size no more than 8."
          ::= { dhcpPoolEntry 1 }

dhcpPoolPoolType OBJECT-TYPE
          SYNTAX      INTEGER
                       {
                            notSpecify(1),
                            netWork(2),
                            host(3)
                       }
          MAX-ACCESS  read-create
          STATUS      current
          DESCRIPTION "Pool Type: notSpecify(1); netWork(2); host(3)."
          ::= { dhcpPoolEntry 2 }

dhcpPoolPoolAddress OBJECT-TYPE
          SYNTAX      IpAddress
          MAX-ACCESS  read-create
          STATUS      current
          DESCRIPTION "The DHCP pool address."
          ::= { dhcpPoolEntry 3 }

dhcpPoolSubnetMask OBJECT-TYPE
          SYNTAX      IpAddress
          MAX-ACCESS  read-create
          STATUS      current
          DESCRIPTION "The DHCP pool subnet mask."
          ::= { dhcpPoolEntry 4 }

dhcpPoolHardwareType OBJECT-TYPE
          SYNTAX      INTEGER
                      {
                        notSpecify(1),
                        ethernet(2),
                        ieee802(3),
                        fddi(4)
                      }
          MAX-ACCESS  read-create
          STATUS      current
          DESCRIPTION "The DHCP pool hardware type."
          ::= { dhcpPoolEntry 5 }

dhcpPoolMacAddress OBJECT-TYPE
          SYNTAX      OCTET STRING(SIZE(6))
          MAX-ACCESS  read-create
          STATUS      current
          DESCRIPTION "The DHCP pool MAC address."
          ::= { dhcpPoolEntry 6 }

dhcpPoolstatus OBJECT-TYPE
          SYNTAX      ValidStatus
          MAX-ACCESS  read-create
          STATUS      current
          DESCRIPTION "Setting this object to valid(1) creates an entry.
                       Setting this object to invalid(2) destroys an entry."
          ::= { dhcpPoolEntry 7 }

--dhcpPoolOptionTable
dhcpPoolOptionTable OBJECT-TYPE
          SYNTAX      SEQUENCE OF DhcpPoolOptionEntry
          MAX-ACCESS  not-accessible
          STATUS      current
          DESCRIPTION "This is the option table of the dhcpPoolTable,
                       the user can specify option configurations in this table."
          ::= { dhcpServerMgt 2 }

dhcpPoolOptionEntry OBJECT-TYPE
          SYNTAX      DhcpPoolOptionEntry
          MAX-ACCESS  not-accessible
          STATUS      current
          DESCRIPTION "A conceptual row of dhcpPoolOptionTable."
          INDEX { dhcpPoolOptionPoolName }
          ::= { dhcpPoolOptionTable 1 }

DhcpPoolOptionEntry ::= SEQUENCE
{
     dhcpPoolOptionPoolName  DisplayString,
     dhcpPoolOptionNextServer IpAddress,
     dhcpPoolOptionNetbiosNodeType  INTEGER,
     dhcpPoolOptionDomainName DisplayString,
     dhcpPoolOptionBootFile DisplayString,
     dhcpPoolOptionLeaseTime Integer32,
     dhcpPoolOptionCidMode INTEGER,
     dhcpPoolOptionCidBuffer  OCTET STRING
}

dhcpPoolOptionPoolName OBJECT-TYPE
          SYNTAX      DisplayString(SIZE(1..8))
          MAX-ACCESS  not-accessible
          STATUS      current
          DESCRIPTION "PoolName, simply specify a string which
                      string size no more than 8."
          ::= { dhcpPoolOptionEntry 1 }

dhcpPoolOptionNextServer OBJECT-TYPE
          SYNTAX      IpAddress
          MAX-ACCESS  read-write
          STATUS      current
          DESCRIPTION "Specifies the IP address of the next server in the boot process,
                        which is typically a Trivial File Transfer Protocol(TFTP) server.
                        One IP address is required."
          ::= { dhcpPoolOptionEntry 2 }

dhcpPoolOptionNetbiosNodeType OBJECT-TYPE
          SYNTAX      INTEGER
                      {
                        none(1),
                        b-node(2),
                        p-node(3),
                        m-node(4),
                        h-node(5)
                      }
          MAX-ACCESS  read-write
          STATUS      current
          DESCRIPTION "Specifies the NetBIOS node type. Valid types are:
                        none(1)
                        b-node(2) - Broadcast
                        p-node(3) - Peer-to-peer
                        m-node(4) - Mixed
                        h-node(5) - Hybrid."
          ::= { dhcpPoolOptionEntry 3 }

dhcpPoolOptionDomainName OBJECT-TYPE
          SYNTAX      DisplayString(SIZE(0..128))
          MAX-ACCESS  read-write
          STATUS      current
          DESCRIPTION "Specifies the domain name string."
          ::= { dhcpPoolOptionEntry 4 }

dhcpPoolOptionBootFile OBJECT-TYPE
          SYNTAX      DisplayString(SIZE(0..128))
          MAX-ACCESS  read-write
          STATUS      current
          DESCRIPTION "To specify the name of the default boot image."
          ::= { dhcpPoolOptionEntry 5 }

dhcpPoolOptionLeaseTime OBJECT-TYPE
          SYNTAX INTEGER(1..31536000|'7FFFFFFF'H)
          UNITS "seconds"
          MAX-ACCESS  read-write
          STATUS      current
          DESCRIPTION "To configure the duration of the lease,
                       in seconds, of an
                       IP address that is assigned from a DHCP Server
                       to a DHCP client. Valid values are from 1 to
                       31536000 (365 days), and a large number
                       '7FFFFFFF'h, which is 'practically infinite'"
          ::= { dhcpPoolOptionEntry 6 }

dhcpPoolOptionCidMode OBJECT-TYPE
          SYNTAX      INTEGER
                      {
                        notSpecify(1),
                        text(2),
                        hex(3)
                      }
          MAX-ACCESS  read-write
          STATUS      current
          DESCRIPTION "Set this variable to text(2) or hex(3)
                        to specify the mode of the client ID,
                        which is useful for the CLI to determine the display method of the
                        client ID.
                        You will get default value 'notSpecify(1)'if this variable
                        has never been set.
                        Setting this to notSpecify(1) is a invalid operation."
          ::= { dhcpPoolOptionEntry 7 }

dhcpPoolOptionCidBuffer OBJECT-TYPE
          SYNTAX      OCTET STRING(SIZE(0..128))
          MAX-ACCESS  read-write
          STATUS      current
          DESCRIPTION "Content of the client ID.
                        You must specify the dhcpPoolOptionCidMode before
                        setting this variable."
          ::= { dhcpPoolOptionEntry 8 }


--dhcpPoolOptionDnsSerTable
dhcpPoolOptionDnsSerTable OBJECT-TYPE
          SYNTAX      SEQUENCE OF DhcpPoolOptionDnsSerEntry
          MAX-ACCESS  not-accessible
          STATUS      current
          DESCRIPTION "To specify the DNS IP servers available to a DHCP client,
                        you can specify up to two addresses for each DHCP pool."
          ::= { dhcpServerMgt 3 }

dhcpPoolOptionDnsSerEntry OBJECT-TYPE
          SYNTAX      DhcpPoolOptionDnsSerEntry
          MAX-ACCESS  not-accessible
          STATUS      current
          DESCRIPTION "A conceptual row of dhcpPoolOptionDnsSerTable."
          INDEX { dhcpPoolOptionDnsSerPoolName,dhcpPoolOptionDnsSerIndex}
          ::= { dhcpPoolOptionDnsSerTable 1 }

DhcpPoolOptionDnsSerEntry ::= SEQUENCE
{
     dhcpPoolOptionDnsSerPoolName  DisplayString,
     dhcpPoolOptionDnsSerIndex Integer32,
     dhcpPoolOptionDnsSerIpAddress  IpAddress
}

dhcpPoolOptionDnsSerPoolName OBJECT-TYPE
          SYNTAX      DisplayString(SIZE(1..8))
          MAX-ACCESS  not-accessible
          STATUS      current
          DESCRIPTION "PoolName, simply specify a string with
                      string size no more than 8."
          ::= { dhcpPoolOptionDnsSerEntry 1 }

dhcpPoolOptionDnsSerIndex OBJECT-TYPE
          SYNTAX      Integer32(1..2)
          MAX-ACCESS  not-accessible
          STATUS      current
          DESCRIPTION "Index of the DNS server."
          ::= { dhcpPoolOptionDnsSerEntry 2 }

dhcpPoolOptionDnsSerIpAddress OBJECT-TYPE
          SYNTAX      IpAddress
          MAX-ACCESS  read-write
          STATUS      current
          DESCRIPTION "IP address of the DNS server."
          ::= { dhcpPoolOptionDnsSerEntry 3 }

--dhcpPoolOptDefaultRouterTable
dhcpPoolOptDefaultRouterTable OBJECT-TYPE
          SYNTAX      SEQUENCE OF DhcpPoolOptDefaultRouterEntry
          MAX-ACCESS  not-accessible
          STATUS      current
          DESCRIPTION "Specifices the default router list for a DHCP Client,
                        you can specify up to two addresses for each DHCP pool."
          ::= { dhcpServerMgt 4 }

dhcpPoolOptDefaultRouterEntry OBJECT-TYPE
          SYNTAX      DhcpPoolOptDefaultRouterEntry
          MAX-ACCESS  not-accessible
          STATUS      current
          DESCRIPTION "A conceptual row of dhcpPoolOptDefaultRouterTable."
          INDEX { dhcpPoolOptDefaultRouterPoolName,dhcpPoolOptDefaultRouterIndex}
          ::= { dhcpPoolOptDefaultRouterTable 1 }

DhcpPoolOptDefaultRouterEntry ::= SEQUENCE
{
     dhcpPoolOptDefaultRouterPoolName  DisplayString,
     dhcpPoolOptDefaultRouterIndex Integer32,
     dhcpPoolOptDefaultRouterIpAddress  IpAddress
}

dhcpPoolOptDefaultRouterPoolName OBJECT-TYPE
          SYNTAX      DisplayString(SIZE(1..8))
          MAX-ACCESS  not-accessible
          STATUS      current
          DESCRIPTION "PoolName, simply specify a string with
                      string size no more than 8."
          ::= { dhcpPoolOptDefaultRouterEntry 1 }

dhcpPoolOptDefaultRouterIndex OBJECT-TYPE
          SYNTAX      Integer32 (1..2)
          MAX-ACCESS  not-accessible
          STATUS      current
          DESCRIPTION "Index of the default router."
          ::= { dhcpPoolOptDefaultRouterEntry 2 }

dhcpPoolOptDefaultRouterIpAddress OBJECT-TYPE
          SYNTAX      IpAddress
          MAX-ACCESS  read-write
          STATUS      current
          DESCRIPTION "Specifies the IP address of a router. One IP address is required."
          ::= { dhcpPoolOptDefaultRouterEntry 3 }

--dhcpPoolOptNetbiosServerTable
dhcpPoolOptNetbiosServerTable OBJECT-TYPE
          SYNTAX      SEQUENCE OF DhcpPoolOptNetbiosServerEntry
          MAX-ACCESS  not-accessible
          STATUS      current
          DESCRIPTION "To configure the NetBIOS WINS name servers that are available
                        to DHCP clients. You can specify up to eight addresses for each
                        DHCP pool."
          ::= { dhcpServerMgt 5 }

dhcpPoolOptNetbiosServerEntry OBJECT-TYPE
          SYNTAX      DhcpPoolOptNetbiosServerEntry
          MAX-ACCESS  not-accessible
          STATUS      current
          DESCRIPTION "A conceptual row of dhcpPoolOptNetbiosServerTable."
          INDEX { dhcpPoolOptNetbiosServerPoolName,dhcpPoolOptNetbiosServerIndex}
          ::= { dhcpPoolOptNetbiosServerTable 1 }

DhcpPoolOptNetbiosServerEntry ::= SEQUENCE
{
     dhcpPoolOptNetbiosServerPoolName  DisplayString,
     dhcpPoolOptNetbiosServerIndex Integer32,
     dhcpPoolOptNetbiosServerIpAddress  IpAddress
}

dhcpPoolOptNetbiosServerPoolName OBJECT-TYPE
          SYNTAX      DisplayString(SIZE(1..8))
          MAX-ACCESS  not-accessible
          STATUS      current
          DESCRIPTION "PoolName, simply specify a string with
                      string size no more than 8."
          ::= { dhcpPoolOptNetbiosServerEntry 1 }

dhcpPoolOptNetbiosServerIndex OBJECT-TYPE
          SYNTAX      Integer32(1..8)
          MAX-ACCESS  not-accessible
          STATUS      current
          DESCRIPTION "Index of the Netbios name Server."
          ::= { dhcpPoolOptNetbiosServerEntry 2 }

dhcpPoolOptNetbiosServerIpAddress OBJECT-TYPE
          SYNTAX      IpAddress
          MAX-ACCESS  read-write
          STATUS      current
          DESCRIPTION "Specifies the IP address of the NetBIOS WINS name server.
                        One IP address is required."
          ::= { dhcpPoolOptNetbiosServerEntry 3 }

--dhcpServerExcludedIpAddrTable
dhcpServerExcludedIpAddrTable OBJECT-TYPE
          SYNTAX      SEQUENCE OF DhcpServerExcludedIpAddrEntry
          MAX-ACCESS  not-accessible
          STATUS      current
          DESCRIPTION "To specify IP addresses that a DHCP Server
                        should not assign to DHCP clients."
          ::= { dhcpServerMgt 6 }

dhcpServerExcludedIpAddrEntry OBJECT-TYPE
          SYNTAX      DhcpServerExcludedIpAddrEntry
          MAX-ACCESS  not-accessible
          STATUS      current
          DESCRIPTION "A conceptual row of dhcpServerExcludedIpAddrTable."
          INDEX { dhcpServerExcludedIpAddrLowIp,dhcpServerExcludedIpAddrHiIp}
          ::= { dhcpServerExcludedIpAddrTable 1 }

DhcpServerExcludedIpAddrEntry ::= SEQUENCE
{
     dhcpServerExcludedIpAddrLowIp  IpAddress,
     dhcpServerExcludedIpAddrHiIp IpAddress,
     dhcpServerExcludedIpAddrStatus  ValidStatus
}

dhcpServerExcludedIpAddrLowIp OBJECT-TYPE
          SYNTAX      IpAddress
          MAX-ACCESS  not-accessible
          STATUS      current
          DESCRIPTION "The excluded IP address,
                        or first IP address in an excluded address range."
          ::= { dhcpServerExcludedIpAddrEntry 1 }

dhcpServerExcludedIpAddrHiIp OBJECT-TYPE
          SYNTAX      IpAddress
          MAX-ACCESS  not-accessible
          STATUS      current
          DESCRIPTION "The last IP address in the excluded address range."
          ::= { dhcpServerExcludedIpAddrEntry 2 }

dhcpServerExcludedIpAddrStatus OBJECT-TYPE
          SYNTAX      ValidStatus
          MAX-ACCESS  read-create
          STATUS      current
          DESCRIPTION "Setting this to valid(1) creates an entry.
                       Setting this to invalid(2) destroys an entry."
          ::= { dhcpServerExcludedIpAddrEntry 3 }

--dhcpServerLeaseBindingTable
dhcpServerLeaseBindingTable OBJECT-TYPE
          SYNTAX      SEQUENCE OF DhcpServerLeaseBindingEntry
          MAX-ACCESS  not-accessible
          STATUS      current
          DESCRIPTION "To configure the address bindings on the DHCP server."
          ::= { dhcpServerMgt 7 }

dhcpServerLeaseBindingEntry OBJECT-TYPE
          SYNTAX      DhcpServerLeaseBindingEntry
          MAX-ACCESS  not-accessible
          STATUS      current
          DESCRIPTION "A conceptual row of dhcpServerLeaseBindingTable."
          INDEX { dhcpServerLeaseBindingIp }
          ::= { dhcpServerLeaseBindingTable 1 }

DhcpServerLeaseBindingEntry ::= SEQUENCE
{
     dhcpServerLeaseBindingIp  IpAddress,
     dhcpServerLeaseBindingMac OCTET STRING,
     dhcpServerLeaseBindingLeaseTime  Integer32,
     dhcpServerLeaseBindingStartTime DisplayString,
     dhcpServerLeaseBindingStatus ValidStatus
}

dhcpServerLeaseBindingIp OBJECT-TYPE
          SYNTAX      IpAddress
          MAX-ACCESS  not-accessible
          STATUS      current
          DESCRIPTION "The IP address of the host as recorded on the DHCP Server."
          ::= { dhcpServerLeaseBindingEntry 1 }

dhcpServerLeaseBindingMac OBJECT-TYPE
          SYNTAX      OCTET STRING (SIZE(6))
          MAX-ACCESS  read-only
          STATUS      current
          DESCRIPTION "The MAC address of the host as recorded on the DHCP Server."
          ::= { dhcpServerLeaseBindingEntry 2 }

dhcpServerLeaseBindingLeaseTime OBJECT-TYPE
          SYNTAX      Integer32
          MAX-ACCESS  read-only
          STATUS      current
          DESCRIPTION "The lease expiration date of the IP address of the host."
          ::= { dhcpServerLeaseBindingEntry 3 }

dhcpServerLeaseBindingStartTime OBJECT-TYPE
          SYNTAX      DisplayString (SIZE(20))
          MAX-ACCESS  read-only
          STATUS      current
          DESCRIPTION "Show current system real time in sec."
          ::= { dhcpServerLeaseBindingEntry 4 }

dhcpServerLeaseBindingStatus OBJECT-TYPE
          SYNTAX      ValidStatus
          MAX-ACCESS  read-create
          STATUS      current
          DESCRIPTION "Setting this to valid(1) creates an entry.
                       Setting this to invalid(2) destroys an entry."
          ::= { dhcpServerLeaseBindingEntry 5 }

dhcpServerServiceStatus OBJECT-TYPE
          SYNTAX      EnabledStatus
          MAX-ACCESS  read-write
          STATUS      current
          DESCRIPTION "Setting this to 1 to enable the DHCP server service.
                       Setting this to 2 to disable the DHCP server service."
          ::= { dhcpServerMgt 8 }

--add by kinghong, not implement yet start

ipHttpRefreshInterval OBJECT-TYPE
          SYNTAX      Integer32(0..1800)
          MAX-ACCESS  read-write
          STATUS      current
          DESCRIPTION "The WEB refresh intervals, in units of a second."
          ::= { ipMgt 12 }

ipNetToMediaExtTable OBJECT-TYPE
    SYNTAX      SEQUENCE OF IpNetToMediaExtEntry
    MAX-ACCESS  not-accessible
    STATUS      current
    DESCRIPTION
            "The extension table for ipNetToMediaTable. This table enhanced
             the original table with extra ipNetToMediaType which is defined
             in ipNetToMediaExtType."
    ::= { ipMgt 13 }

ipNetToMediaExtEntry OBJECT-TYPE
    SYNTAX      IpNetToMediaExtEntry
    MAX-ACCESS  not-accessible
    STATUS      current
    DESCRIPTION
            "Each entry contains the extension type of ipNetToMediaTable."
    AUGMENTS       { ipNetToMediaEntry}
    ::= { ipNetToMediaExtTable 1 }

IpNetToMediaExtEntry ::= SEQUENCE
   {
        ipNetToMediaExtType         INTEGER
    }


ipNetToMediaExtType OBJECT-TYPE
    SYNTAX      INTEGER {
                other(1),        -- none of the following
                invalid(2),      -- an invalidated mapping
                dynamic(3),
                static(4),
                local (101),
                broadcast(102),
                vrrp(103)
            }
    MAX-ACCESS  read-create
    STATUS      current
    DESCRIPTION
            "The extension type of ipNetToMediaTable, this table extends the
             original ipNetMediaTable with several extension types: local(101),
             broadcast(102), and vrrp(103). The MAX-ACCESS of this table follows
             the Rfc2011 Standard MIB. Note that it may be read-only in some
             systems which do not support write operation on ARP Table."
    ::= { ipNetToMediaExtEntry 3 }

--add by kinghong, not implement yet end

--
--pingMgt
--

pingMgt              OBJECT IDENTIFIER ::= { ipMgt 15 }

pingIpAddress OBJECT-TYPE
    SYNTAX     IpAddress
    MAX-ACCESS read-write
    STATUS     current
    DESCRIPTION
        "The address of the device to be pinged."
    ::= { pingMgt 1 }

pingPacketSize OBJECT-TYPE
    SYNTAX     Integer32 (32..512)
    MAX-ACCESS read-write
    STATUS     current
    DESCRIPTION
        "Specifies the size of ping packets to send to the target in this ping
         operation. The lower and upper boundaries of this object are
         protocol-dependent."
    DEFVAL { 32 }
    ::= { pingMgt 2 }

pingRoundTripTime OBJECT-TYPE
    SYNTAX     Integer32
    UNITS      "milliseconds"
    MAX-ACCESS read-only
    STATUS     current
    DESCRIPTION
        "The last round trip time of a single ping operation. When the ping
         opertion is time out, a value of -1 will be returned."
    ::= { pingMgt 3 }

pingCompleted OBJECT-TYPE
    SYNTAX     TruthValue
    MAX-ACCESS read-only
    STATUS     current
    DESCRIPTION
        "A value of true(1) will be read when this ping operation
        have been either responded to or timed out. A value of false(2) will be
        read when there is a ping operation is currently running and all
        associate objects in pingMgt cannot be modified during this period."
    ::= { pingMgt 4 }

pingAction OBJECT-TYPE
    SYNTAX     INTEGER {
                   noAction(1),
                   pingStart(2)
                 }
    MAX-ACCESS read-write
    STATUS     current
    DESCRIPTION
        "The action of the pingMgt. Set this objects to pingStart(2) to begin
         the ping operation. Once the action is set to pingStart(2), the
         associate pingMgt objects cannot be modified until this ping operation is
         completed (pingCompleted is true). When the ping has ended or no ping
         operation is performing, this object will get a value of noAction(1)."
    ::= { pingMgt 5 }

iPAddrTable  OBJECT-TYPE
    SYNTAX     SEQUENCE OF IPAddrEntry
    MAX-ACCESS not-accessible
    STATUS     current
    DESCRIPTION
        "A table of iPAddrEntry."
    ::= { ipMgt 16 }

iPAddrEntry  OBJECT-TYPE
    SYNTAX     IPAddrEntry
    MAX-ACCESS not-accessible
    STATUS     current
    DESCRIPTION
        "A set of configuration parameters for a particular
        network interface on this device. If the device has no network
        interface, this table is empty.

        The index is composed of the ifIndex assigned to the
        corresponding interface."
    INDEX  { iPAddrIPAddress, iPAddrSubnetMask }
    ::= { iPAddrTable 1 }

IPAddrEntry ::= SEQUENCE {
    iPAddrIPAddress         IpAddress,
    iPAddrSubnetMask        IpAddress,
    iPAddrIfIndex           Integer32,
    iPAddrPrimaryInterface  INTEGER,
    iPAddrUnnumbered        INTEGER,
    iPAddrStatus            RowStatus
}


iPAddrIPAddress  OBJECT-TYPE
    SYNTAX     IpAddress
    MAX-ACCESS not-accessible
    STATUS     current
    DESCRIPTION
        "The IP address of this Net interface.  The default value
        for this object is 0.0.0.0.  If either the IPAddrIPAddress
        or IPAddrSubnetMask is 0.0.0.0, then when the device
        boots, it may use BOOTP to try to figure out what these
        values should be. If BOOTP fails, before the device
        can talk on the network, this value must be configured
        (e.g., through a terminal attached to the device)."
    ::= { iPAddrEntry 1 }

iPAddrSubnetMask  OBJECT-TYPE
    SYNTAX     IpAddress
    MAX-ACCESS not-accessible
    STATUS     current
    DESCRIPTION
        "The subnet mask of this Net interface.  The default value
        for this object is 0.0.0.0.  If either the IPAddrIPAddress
        or IPAddrSubnetMask are 0.0.0.0, then when the device
        boots, it may use BOOTP to try to figure out what these
        values should be. If BOOTP fails, before the device
        can talk on the network, this value must be configured
        (e.g., through a terminal attached to the device)."
    ::= { iPAddrEntry 2 }

iPAddrIfIndex  OBJECT-TYPE
    SYNTAX     Integer32
    MAX-ACCESS read-create
    STATUS     current
    DESCRIPTION "The VLAN interface being used by this table entry. Only the
                 VLAN interfaces which have an IP configured will appear in
                 the table."
    ::= { iPAddrEntry 3 }

iPAddrPrimaryInterface OBJECT-TYPE
    SYNTAX     INTEGER
               {
                   primary(1),
                   secondary(2)
               }
    MAX-ACCESS read-create
    STATUS     current
    DESCRIPTION
        "Whether this is a primary interface."
    ::= { iPAddrEntry 4 }

iPAddrUnnumbered OBJECT-TYPE
    SYNTAX     INTEGER
               {
                   unnumbered(1),
                   notUnnumbered(2)
               }
    MAX-ACCESS read-only
    STATUS     current
    DESCRIPTION
        "Whether this is an unnumbered interface."
    ::= { iPAddrEntry 5 }

iPAddrStatus  OBJECT-TYPE
    SYNTAX     RowStatus
    MAX-ACCESS read-create
    STATUS     current
    DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation: 'notReady', 'notInService' or
            'active'. That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { iPAddrEntry 6 }
--
-- bcastStormMgt
--

-- Management for broadcast storm control for ports.


bcastStormTable OBJECT-TYPE
        SYNTAX      SEQUENCE OF BcastStormEntry
        MAX-ACCESS  not-accessible
        STATUS      current
        DESCRIPTION "Table to manage the control of broadcast storms for ports."
        ::= { bcastStormMgt 1 }

bcastStormEntry OBJECT-TYPE
        SYNTAX      BcastStormEntry
        MAX-ACCESS  not-accessible
        STATUS      current
        DESCRIPTION "The conceptual row of bcastStormTable."
        INDEX       { bcastStormIfIndex }
        ::= { bcastStormTable 1 }

BcastStormEntry ::= SEQUENCE
{
    bcastStormIfIndex      Integer32,
    bcastStormStatus       EnabledStatus,
    bcastStormSampleType   INTEGER,
    bcastStormPktRate      Integer32,
    bcastStormOctetRate    Integer32,
    bcastStormPercent         Integer32,
    bcastStormBitRateInKilo   Integer32
}

bcastStormIfIndex OBJECT-TYPE
        SYNTAX      Integer32
        MAX-ACCESS  not-accessible
        STATUS      current
        DESCRIPTION "The port and the trunk (including trunk members) interface of
                     the portTable. The interface identified by a particular value
                     of this index is the same interface as identified by the same
                     value of ifIndex in the IF-MIB."
        ::= { bcastStormEntry 1 }

bcastStormStatus OBJECT-TYPE
        SYNTAX      EnabledStatus
        MAX-ACCESS  read-write
        STATUS      current
        DESCRIPTION "Whether broadcast storm protection is enabled."
        ::= { bcastStormEntry 2 }

bcastStormSampleType OBJECT-TYPE
        SYNTAX      INTEGER
                    {
                        pkt-rate(1),
                        octet-rate(2),
                        percent(3),
                        bit-rate-in-kilo(4)
                    }
        MAX-ACCESS  read-write
        STATUS      current
        DESCRIPTION "Sample type. If this is pkt-rate(1), then bcastStormPktRate
                     is used to specify the broadcast storm threshold. If this
                     is octet-rate(2), then bcastStormOctetRate determines the
                     broadcast storm threshold. If this is percent(3), then
                     bcastStormPercent determines the threshold. If this is
                     bit-rate-in-kilo(4), then bcastStormBitRateInKilo is valid."
        ::= { bcastStormEntry 3 }

bcastStormPktRate OBJECT-TYPE
        SYNTAX      Integer32
        MAX-ACCESS  read-write
        STATUS      current
        DESCRIPTION "Broadcast storm threshold as packets per second.
                     If this entry is for a trunk, this is the value
                     for each member port."
        ::= { bcastStormEntry 4 }

bcastStormOctetRate OBJECT-TYPE
        SYNTAX      Integer32
        MAX-ACCESS  read-write
        STATUS      current
        DESCRIPTION "Broadcast storm threshold as octets per second.
                     If this entry is for a trunk, this is the value
                     for each member port."
        ::= { bcastStormEntry 5 }

bcastStormPercent OBJECT-TYPE
        SYNTAX      Integer32
        MAX-ACCESS  read-write
        STATUS      current
        DESCRIPTION "Broadcast storm threshold as percentage of bandwidth."
        ::= { bcastStormEntry 6 }

bcastStormBitRateInKilo OBJECT-TYPE
        SYNTAX      Integer32
        MAX-ACCESS  read-write
        STATUS      current
        DESCRIPTION "Broadcast storm threshold in kilobits per second.
                     If this entry is for a trunk, this is the value
                     for each member port. For a 100 Mbps port, the
                     range is 64 to 100000. For a 1000 Mbps port, the
                     range is 64 to 1000000."
        ::= { bcastStormEntry 7}

--
-- mcastStormMgt
--

-- Management for multicast storm control for ports.


mcastStormTable OBJECT-TYPE
        SYNTAX      SEQUENCE OF McastStormEntry
        MAX-ACCESS  not-accessible
        STATUS      current
        DESCRIPTION "Table to manage the control of multicast storms for ports."
        ::= { bcastStormMgt 2 }

mcastStormEntry OBJECT-TYPE
        SYNTAX      McastStormEntry
        MAX-ACCESS  not-accessible
        STATUS      current
        DESCRIPTION "The conceptual row of multiStormTable."
        INDEX       { mcastStormIfIndex }
        ::= { mcastStormTable 1 }

McastStormEntry ::= SEQUENCE
{
    mcastStormIfIndex      Integer32,
    mcastStormStatus       EnabledStatus,
    mcastStormPktRate      Integer32
}

mcastStormIfIndex OBJECT-TYPE
        SYNTAX      Integer32
        MAX-ACCESS  not-accessible
        STATUS      current
        DESCRIPTION "The port and the trunk (including trunk members) interface of
                     the portTable. The interface identified by a particular value
                     of this index is the same interface as identified by the same
                     value of ifIndex in the IF-MIB."
        ::= { mcastStormEntry 1 }

mcastStormStatus OBJECT-TYPE
        SYNTAX      EnabledStatus
        MAX-ACCESS  read-write
        STATUS      current
        DESCRIPTION "Whether multicast storm protection is enabled."
        ::= { mcastStormEntry 2 }

mcastStormPktRate OBJECT-TYPE
        SYNTAX      Integer32
        MAX-ACCESS  read-write
        STATUS      current
        DESCRIPTION "Multicast storm threshold as packets per second.
                     If this entry is for a trunk, this is the value
                     for each member port."
        ::= { mcastStormEntry 4 }

bcastStormGlobalSampleType OBJECT-TYPE
        SYNTAX      INTEGER
                    {
                        pkt-rate(1),
                        octet-rate(2),
                        percent(3)
                    }
        MAX-ACCESS  read-write
        STATUS      current
        DESCRIPTION "Sample type. If this is pkt-rate(1), then bcastStormGlobalPktRate
                     is used to specify the broadcast storm threshold. If this
                     is octet-rate(2), then bcastStormGlobalOctetRate determines the
                     broadcast storm threshold. If this is percent(3), then
                     bcastStormGlobalPercent determines the threshold."
        ::= { bcastStormMgt 3 }

bcastStormGlobalPktRate OBJECT-TYPE
        SYNTAX      Integer32
        MAX-ACCESS  read-write
        STATUS      current
        DESCRIPTION "Broadcast storm threshold as packets per second."
        ::= { bcastStormMgt 4 }

bcastStormGlobalOctetRate OBJECT-TYPE
        SYNTAX      Integer32
        MAX-ACCESS  read-write
        STATUS      current
        DESCRIPTION "Broadcast storm threshold as octets per second."
        ::= { bcastStormMgt 5 }

bcastStormGlobalPercent OBJECT-TYPE
        SYNTAX      Integer32
        MAX-ACCESS  read-write
        STATUS      current
        DESCRIPTION "Broadcast storm threshold as percentage of bandwidth."
        ::= { bcastStormMgt 6 }

--
-- vlanMgt
--

-- Management for Virtual Local Area Network (VLAN).
-- This has variables not already defined in the implemented
-- standard MIB(s).

vlanTable OBJECT-TYPE
        SYNTAX      SEQUENCE OF VlanEntry
        MAX-ACCESS  not-accessible
        STATUS      current
        DESCRIPTION "Table for VLAN configuration."
        ::= { vlanMgt 1 }

vlanEntry OBJECT-TYPE
        SYNTAX      VlanEntry
        MAX-ACCESS  not-accessible
        STATUS      current
        DESCRIPTION "Entry for VLAN configuration."
        INDEX       { vlanIndex }
        ::= { vlanTable 1 }

VlanEntry ::= SEQUENCE
{
    vlanIndex               Unsigned32,
    vlanAddressMethod       INTEGER
}

vlanIndex OBJECT-TYPE
        SYNTAX      Unsigned32
        MAX-ACCESS  not-accessible
        STATUS      current
        DESCRIPTION "Based on dot1qVlanIndex in the Q-BRIDGE-MIB.
                     This table has only one entry - the entry for
                     the VLAN of the management interface."
        ::= { vlanEntry 1 }

vlanAddressMethod OBJECT-TYPE
        SYNTAX      INTEGER
                    {
                        user(1),
                        bootp(2),
                        dhcp(3)
                    }
        MAX-ACCESS  read-write
        STATUS      current
        DESCRIPTION "Method to get the IP address."
        ::= { vlanEntry 2 }

vlanPortTable OBJECT-TYPE
        SYNTAX      SEQUENCE OF VlanPortEntry
        MAX-ACCESS  not-accessible
        STATUS      current
        DESCRIPTION "Table for port configuration in VLAN."
        ::= { vlanMgt 2 }

vlanPortEntry OBJECT-TYPE
        SYNTAX      VlanPortEntry
        MAX-ACCESS  not-accessible
        STATUS      current
        DESCRIPTION "Entry for port configuration in VLAN."
        INDEX       { vlanPortIndex }
        ::= { vlanPortTable 1 }

VlanPortEntry ::= SEQUENCE
{
    vlanPortIndex               Integer32,
    vlanPortMode                INTEGER,
    vlanPortPrivateVlanType     INTEGER,
    vlanSTagPriorityPortState   INTEGER
}

vlanPortIndex OBJECT-TYPE
        SYNTAX      Integer32
        MAX-ACCESS  not-accessible
        STATUS      current
        DESCRIPTION "The port and the trunk (excluding trunk members) interface of
                     the portTable. The interface identified by a particular value
                     of this index is the same interface as identified by the same
                     value of dot1qPvid in the Q-BRIDGE-MIB."
        ::= { vlanPortEntry 1 }

vlanPortMode OBJECT-TYPE
        SYNTAX      INTEGER
                    {
                        hybrid(1),
                        dot1qTrunk(2),
                        access(3)
                    }
        MAX-ACCESS  read-write
        STATUS      current
        DESCRIPTION "This variable sets the 802.1Q VLAN mode.
                    Setting it to hybrid(1) sets a hybrid link.
                    Setting it to dot1qTrunk(2) sets a trunk link.
                    Setting it to access(3) sets an access link."
        ::= { vlanPortEntry 2 }

--　SYS_CPNT_COMMUNITY_PRIVATE_VLAN　(use PVLAN_MGR API) start
vlanPortPrivateVlanType OBJECT-TYPE
        SYNTAX     INTEGER
                   {
                       normal(1),
                       isolated(2),
                       community(3),
                       promiscous(4)
                   }
        MAX-ACCESS  read-write
        STATUS      current
        DESCRIPTION "The port type defined for private VLAN."
       ::= { vlanPortEntry 3 }
-- SYS_CPNT_COMMUNITY_PRIVATE_VLAN (use PVLAN_MGR API) end

vlanSTagPriorityPortState OBJECT-TYPE
		SYNTAX      INTEGER
                    {
                        enabled(1),
                        disabled(2)
                    }
        MAX-ACCESS  read-write
        STATUS      current
        DESCRIPTION "Parameter to enable or disable the function that retrieve the priority bits from
                     the transparent S-tag frame and make use of them in the applied native Q-tag."
        ::= { vlanPortEntry 4 }

vlanRange OBJECT-TYPE
        SYNTAX      Integer32
        MAX-ACCESS  read-only
        STATUS      current
        DESCRIPTION "Reserved VLANs used by the Mobility Controller"
        ::= { vlanMgt 3 }

vlanReservedId OBJECT-TYPE
        SYNTAX      Integer32
        MAX-ACCESS  read-write
        STATUS      current
        DESCRIPTION "VLAN ID is the first VLAN in the reserved range for
                     wireless VLANs. The length of the range is determined by
                     the vlanRange. For example, if the vlanRange is 65 and vlanReservedId
                     is 4026, then the range of reserved VLANs will be 4026 to 4090."
        ::= { vlanMgt 4 }

--
-- protocolVlanMgt ES3524MO-PoE-FLF-26B-00174
--
protocolVlanTable   OBJECT-TYPE
    SYNTAX      SEQUENCE OF ProtocolVlanEntry
    MAX-ACCESS  not-accessible
	STATUS      current
	DESCRIPTION "The configuration table which contains the binding entry
	             of the protocol-group and VLANs."
	::= { vlanMgt 5 }

protocolVlanEntry   OBJECT-TYPE
    SYNTAX      ProtocolVlanEntry
    MAX-ACCESS  not-accessible
    STATUS      current
    DESCRIPTION "The binding entry of the protocol-group and VLANs."
    INDEX       { protocolVlanGroupId }
    ::= { protocolVlanTable 1 }

ProtocolVlanEntry ::= SEQUENCE
{
    protocolVlanGroupId      Integer32,
    protocolVlanGroupVid     Integer32
}

protocolVlanGroupId     OBJECT-TYPE
    SYNTAX      Integer32
    MAX-ACCESS  not-accessible
    STATUS      current
    DESCRIPTION "The specified protocol group of a binding entry."
    ::= { protocolVlanEntry 1 }

protocolVlanGroupVid    OBJECT-TYPE
    SYNTAX      Integer32
    MAX-ACCESS  read-write
    STATUS      current
    DESCRIPTION "The vlan index of the binding entry. The vid zero is
                 used to delete the binding entry."
    ::= { protocolVlanEntry 2 }

vlanDot1qTunnelGlobalConfig OBJECT IDENTIFIER ::= { vlanMgt 7 }

vlanDot1qTunnelStatus OBJECT-TYPE
        SYNTAX      EnabledStatus
        MAX-ACCESS  read-write
        STATUS      current
        DESCRIPTION
            "This parameter is used to globally enable/disable
             802.1Q Tunneling on the device."
        ::= { vlanDot1qTunnelGlobalConfig 1 }

vlanDot1qTunnelPortTable OBJECT-TYPE
        SYNTAX      SEQUENCE OF VlanDot1qTunnelPortEntry
        MAX-ACCESS  not-accessible
        STATUS      current
        DESCRIPTION "Table for port configuration in 802.1Q Tunneling."
        ::= { vlanMgt 8 }

vlanDot1qTunnelPortEntry OBJECT-TYPE
        SYNTAX      VlanDot1qTunnelPortEntry
        MAX-ACCESS  not-accessible
        STATUS      current
        DESCRIPTION "Entry for port configuration in 802.1Q Tunneling."
        INDEX       { vlanDot1qTunnelPortIndex }
        ::= { vlanDot1qTunnelPortTable 1 }

VlanDot1qTunnelPortEntry ::= SEQUENCE
{
    vlanDot1qTunnelPortIndex                Integer32,
    vlanDot1qTunnelPortMode                 INTEGER,
    vlanDot1qTunnelPortEtherType            Unsigned32
}

vlanDot1qTunnelPortIndex OBJECT-TYPE
        SYNTAX      Integer32
        MAX-ACCESS  not-accessible
        STATUS      current
        DESCRIPTION "The port and the trunk (excluding trunk members) interface of
                     the portTable. The interface identified by a particular value
                     of this index is the same interface as identified by the same
                     value of ifIndex in the IF-MIB."
        ::= { vlanDot1qTunnelPortEntry 1 }

vlanDot1qTunnelPortMode OBJECT-TYPE
        SYNTAX      INTEGER
                    {
                        none(1),
                        dot1qTunnel(2),
                        dot1qTunnelUplink(3)
                    }
        MAX-ACCESS  read-write
        STATUS      current
        DESCRIPTION "This variable sets the 802.1Q Tunneling mode.
                     Setting it to none(1) indicates no mode in this port.
                     Setting it to dot1qTunnel(2) sets as dot1q-tunnel mode port which link to customer.
                     Setting it to dot1qTunnelUplink(3) sets as dot1q-tunnel mode port which link to service-provider.
                     If vlanDot1qTunnelStatus is disabled, it means vlanDot1qTunnelPortMode is inactive."
        ::= { vlanDot1qTunnelPortEntry 2 }

vlanDot1qTunnelPortEtherType  OBJECT-TYPE
       SYNTAX     Unsigned32 ('0800'h..'ffff'h)
       MAX-ACCESS read-write
       STATUS     current
       DESCRIPTION "TPID for 802.1Q encapsulation. It's used to select a nonstandard
                    (nondefault) 2-byte ethertype to identify 802.1Q tagged frames."
       ::= { vlanDot1qTunnelPortEntry 3 }

--
-- voiceVlanMgt ES3524MO-PoE-FLF-26B-00174
--
voiceVlanMgt        OBJECT IDENTIFIER ::= { vlanMgt 6 }

voiceVlanOuiTable   OBJECT-TYPE
    SYNTAX      SEQUENCE OF VoiceVlanOuiEntry
    MAX-ACCESS  not-accessible
	STATUS      current
	DESCRIPTION "A table containing the mac address which can be identified
	             by voice vlan."
	::= { voiceVlanMgt 1 }

voiceVlanOuiEntry OBJECT-TYPE
		SYNTAX  VoiceVlanOuiEntry
		MAX-ACCESS not-accessible
		STATUS current
		DESCRIPTION "A table containing the mac address which can be identified
		             by voice vlan."
        INDEX   { voiceVlanOuiAddress }
        ::= { voiceVlanOuiTable 1 }

VoiceVlanOuiEntry	::=
	SEQUENCE {
              voiceVlanOuiAddress	    MacAddress,
              voiceVlanOuiMask	        MacAddress,
              voiceVlanOuiDescription	DisplayString,
              voiceVlanOuiStatus  	    ValidStatus
		     }

voiceVlanOuiAddress OBJECT-TYPE
        SYNTAX      MacAddress
		MAX-ACCESS  read-only
		STATUS      current
		DESCRIPTION "MAC address can be identified by voice vlan."
		::= { voiceVlanOuiEntry 1 }

voiceVlanOuiMask OBJECT-TYPE
		SYNTAX      MacAddress
		MAX-ACCESS  read-write
		STATUS      current
		DESCRIPTION "The mask of MAC address."
		::= { voiceVlanOuiEntry 2 }

voiceVlanOuiDescription OBJECT-TYPE
		SYNTAX      DisplayString (SIZE(0..30))
		MAX-ACCESS  read-write
		STATUS      current
		DESCRIPTION "The description of oui."
		::= { voiceVlanOuiEntry 3 }

voiceVlanOuiStatus OBJECT-TYPE
		SYNTAX      ValidStatus
		MAX-ACCESS  read-create
		STATUS      current
		DESCRIPTION "Current operation status of the row."
		::= { voiceVlanOuiEntry 4 }

voiceVlanEnabledId  OBJECT-TYPE
        SYNTAX      INTEGER
        MAX-ACCESS  read-write
        STATUS      current
        DESCRIPTION "Voice vlan enable status: enabled (2..4095), disabled (-1)."
        ::= { voiceVlanMgt 2 }

voiceVlanAgingTime  OBJECT-TYPE
        SYNTAX  INTEGER (5..43200)
        MAX-ACCESS read-write
        STATUS current
        DESCRIPTION " Voice vlan aging time, the unit of which is minute."
	DEFVAL      { 1440 }
        ::= { voiceVlanMgt 3 }

voiceVlanPortTable OBJECT-TYPE
        SYNTAX  SEQUENCE OF VoiceVlanPortEntry
        MAX-ACCESS not-accessible
        STATUS   current
        DESCRIPTION " A list of voice vlan mode entries."
        ::= { voiceVlanMgt 7 }

voiceVlanPortEntry OBJECT-TYPE
        SYNTAX      VoiceVlanPortEntry
        MAX-ACCESS  not-accessible
        STATUS      current
        DESCRIPTION "An entry containing voice vlan mode information,
                    which is applicable to a voice vlan enabled interface."
        INDEX   { voiceVlanPortIfIndex }
        ::= { voiceVlanPortTable 1 }

VoiceVlanPortEntry ::=
        SEQUENCE {
         voiceVlanPortIfIndex   Integer32 ,
         voiceVlanPortMode      INTEGER,
         voiceVlanPortSecurity  EnabledStatus,
         voiceVlanPortPriority  INTEGER,
         voiceVlanPortRuleOui   EnabledStatus,
         voiceVlanPortRuleLldp  EnabledStatus
		 }

voiceVlanPortIfIndex OBJECT-TYPE
        SYNTAX      Integer32(1..2147483647)
        MAX-ACCESS  not-accessible
        STATUS      current
        DESCRIPTION "The index of interface on which voice vlan function
                    is enabled."
        REFERENCE "IfIndex in RFC1213"
	::= { voiceVlanPortEntry 1 }

voiceVlanPortMode OBJECT-TYPE
        SYNTAX      INTEGER
                	{
                	auto (1),
                	manual (2),
                	none (3)
                	}
        MAX-ACCESS  read-write
        STATUS      current
        DESCRIPTION "Voice vlan configuration mode status."
        ::= { voiceVlanPortEntry 2 }

voiceVlanPortSecurity OBJECT-TYPE
        SYNTAX      EnabledStatus
        MAX-ACCESS  read-write
        STATUS      current
        DESCRIPTION "If the security is enabled, the port is only allow voice
                     traffuc for the voice vlan."
        ::= { voiceVlanPortEntry 3 }

voiceVlanPortPriority OBJECT-TYPE
        SYNTAX      INTEGER(0..6)
        MAX-ACCESS  read-write
        STATUS      current
        DESCRIPTION "The priority of the voice vlan traffic in the port."
        ::= { voiceVlanPortEntry 4 }

voiceVlanPortRuleOui OBJECT-TYPE
        SYNTAX      EnabledStatus
        MAX-ACCESS  read-write
        STATUS      current
        DESCRIPTION "The address of voice device is learned from
                     Oui table."
        ::=  { voiceVlanPortEntry 5 }

voiceVlanPortRuleLldp OBJECT-TYPE
        SYNTAX      EnabledStatus
        MAX-ACCESS  read-write
        STATUS      current
        DESCRIPTION "The address of voice device is learned from
                     LLDP discovery."
        ::= { voiceVlanPortEntry 6 }

--ASE3528B-E1-FLF-P5-00028
vlanDot1qTunnelGlobalConfig OBJECT IDENTIFIER ::= { vlanMgt 7 }

vlanDot1qTunnelStatus OBJECT-TYPE
        SYNTAX      EnabledStatus
        MAX-ACCESS  read-write
        STATUS      current
        DESCRIPTION
            "This parameter is used to globally enable/disable
             802.1Q Tunneling on the device."
        ::= { vlanDot1qTunnelGlobalConfig 1 }

vlanDot1qTunnelPriorityMapStatus OBJECT-TYPE
        SYNTAX      EnabledStatus
        MAX-ACCESS  read-write
        STATUS      current
        DESCRIPTION
            "This parameter is used globally to enable/disable
             802.1Q tag priority which is inherited from the inner tag to the outer on the device."
        ::= { vlanDot1qTunnelGlobalConfig 2 }


vlanDot1qTunnelPortTable OBJECT-TYPE
        SYNTAX      SEQUENCE OF VlanDot1qTunnelPortEntry
        MAX-ACCESS  not-accessible
        STATUS      current
        DESCRIPTION "Table for port configuration in 802.1Q Tunneling."
        ::= { vlanMgt 8 }

vlanDot1qTunnelPortEntry OBJECT-TYPE
        SYNTAX      VlanDot1qTunnelPortEntry
        MAX-ACCESS  not-accessible
        STATUS      current
        DESCRIPTION "Entry for port configuration in 802.1Q Tunneling."
        INDEX       { vlanDot1qTunnelPortIndex }
        ::= { vlanDot1qTunnelPortTable 1 }

VlanDot1qTunnelPortEntry ::= SEQUENCE
{
    vlanDot1qTunnelPortIndex                Integer32,
    vlanDot1qTunnelPortMode                 INTEGER,
    vlanDot1qTunnelPortEtherType            Unsigned32
}

vlanDot1qTunnelPortIndex OBJECT-TYPE
        SYNTAX      Integer32
        MAX-ACCESS  not-accessible
        STATUS      current
        DESCRIPTION "The port and the trunk (excluding trunk members) interface of
                     the portTable. The interface identified by a particular value
                     of this index is the same interface as identified by the same
                     value of ifIndex in the IF-MIB."
        ::= { vlanDot1qTunnelPortEntry 1 }

vlanDot1qTunnelPortMode OBJECT-TYPE
        SYNTAX      INTEGER
                    {
                        none(1),
                        dot1qTunnel(2),
                        dot1qTunnelUplink(3)
                    }
        MAX-ACCESS  read-write
        STATUS      current
        DESCRIPTION "This variable sets the 802.1Q Tunneling mode.
                     Setting it to none(1) indicates no mode in this port.
                     Setting it to dot1qTunnel(2) sets as dot1q-tunnel mode port which link to customer.
                     Setting it to dot1qTunnelUplink(3) sets as dot1q-tunnel mode port which link to service-provider.
                     If vlanDot1qTunnelStatus is disabled, it means vlanDot1qTunnelPortMode is inactive."
        ::= { vlanDot1qTunnelPortEntry 2 }

vlanDot1qTunnelPortEtherType  OBJECT-TYPE
       SYNTAX     Unsigned32 ('0800'h..'ffff'h)
       MAX-ACCESS read-write
       STATUS     current
       DESCRIPTION "TPID for 802.1Q encapsulation. It's used to select a nonstandard
                    (nondefault) 2-byte ethertype to identify 802.1Q tagged frames."
       ::= { vlanDot1qTunnelPortEntry 3 }

--
-- dot1vProtocolExPortTable
--

dot1vProtocolExPortTable   OBJECT-TYPE
    SYNTAX      SEQUENCE OF Dot1vProtocolExPortEntry
    MAX-ACCESS  not-accessible
	STATUS      current
	DESCRIPTION "A table that contains protocol Vlan priority information."
	::= { vlanMgt 9 }

dot1vProtocolExPortEntry   OBJECT-TYPE
    SYNTAX      Dot1vProtocolExPortEntry
    MAX-ACCESS  not-accessible
    STATUS      current
    DESCRIPTION "A list of protocol VLAN user priority sets for each port."
    AUGMENTS   { dot1vProtocolPortEntry }
    ::= { dot1vProtocolExPortTable 1 }

Dot1vProtocolExPortEntry ::= SEQUENCE
{
    dot1vProtocolExPortGroupPriority     INTEGER
}

dot1vProtocolExPortGroupPriority     OBJECT-TYPE
    SYNTAX      INTEGER (0..7)
    MAX-ACCESS  read-write
    STATUS      current
    DESCRIPTION "Specifies the priority in the added tag for qualified frames."
    ::= { dot1vProtocolExPortEntry   1 }

--
-- priorityMgt
--

-- Management for traffic priority. This allows a user
-- to specify which data packets have greater precedence
-- when traffic is buffered in the switch due to congestion.

prioIpPrecDscpStatus OBJECT-TYPE
        SYNTAX      INTEGER
                    {
                        disabled(1),
                        precedence(2),
                        dscp(3)
                    }
        MAX-ACCESS  read-write
        STATUS      current
        DESCRIPTION "Selects whether no frame priority mapping, IP ToS
                     precedence mapping or DSCP mapping is performed."
        ::= { priorityMgt 1 }

prioIpPrecTable OBJECT-TYPE
        SYNTAX      SEQUENCE OF PrioIpPrecEntry
        MAX-ACCESS  not-accessible
        STATUS      current
        DESCRIPTION "Table for IP precedence priority mapping."
        ::= { priorityMgt 2 }

prioIpPrecEntry OBJECT-TYPE
        SYNTAX      PrioIpPrecEntry
        MAX-ACCESS  not-accessible
        STATUS      current
        DESCRIPTION "Entry for IP precedence priority mapping."
        INDEX       { prioIpPrecPort, prioIpPrecValue }
        ::= { prioIpPrecTable 1 }

PrioIpPrecEntry ::= SEQUENCE
{
    prioIpPrecPort           Integer32,
    prioIpPrecValue          Integer32,
    prioIpPrecCos            Integer32
}

prioIpPrecPort OBJECT-TYPE
        SYNTAX      Integer32
        MAX-ACCESS  not-accessible
        STATUS      current
        DESCRIPTION "The port or the trunk (excluding trunk members) interface of
                     the portTable. The interface identified by a particular value
                     of this index is the same interface as identified by the same
                     value of ifIndex in the IF-MIB."
        ::= { prioIpPrecEntry 2 }

prioIpPrecValue OBJECT-TYPE
        SYNTAX      Integer32 (0..7)
        MAX-ACCESS  not-accessible
        STATUS      current
        DESCRIPTION "Value of IP ToS Precedence as specified in the packet
                     header."
        ::= { prioIpPrecEntry 3 }

prioIpPrecCos OBJECT-TYPE
        SYNTAX      Integer32 (0..7)
        MAX-ACCESS  read-write
        STATUS      current
        DESCRIPTION "Class of Service (CoS) as defined by
                     dot1dTrafficClassPriority in the P-BRIDGE-MIB.
                     The IP ToS precedence value in the same
                     table row will be mapped to this CoS. This CoS is then
                     further mapped to the hardware queue according to
                     dot1dTrafficClassTable."
        REFERENCE  "P-BRIDGE-MIB.dot1dPriority.dot1dTrafficClassTable."
        ::= { prioIpPrecEntry 4 }

prioIpPrecRestoreDefault OBJECT-TYPE
        SYNTAX      Integer32
        MAX-ACCESS  read-write
        STATUS      current
        DESCRIPTION "Enables the IP Precedence settings of a port to be restored
                     to their default values. To reset the settings of a port,
                     assign prioIpPrecRestoreDefault to the value of ifIndex
                     defined by the ifIndex in the IF-MIB. For example,  if 1 is
                     written to it, then the IP priorities of port 1 will be
                     restored to default. When read, this object always returns 0."
        ::= { priorityMgt 3 }

prioIpDscpTable OBJECT-TYPE
        SYNTAX      SEQUENCE OF PrioIpDscpEntry
        MAX-ACCESS  not-accessible
        STATUS      current
        DESCRIPTION "Table for IP DSCP priority mapping."
        ::= { priorityMgt 4 }

prioIpDscpEntry OBJECT-TYPE
        SYNTAX      PrioIpDscpEntry
        MAX-ACCESS  not-accessible
        STATUS      current
        DESCRIPTION "Entry for IP DSCP priority mapping."
        INDEX       { prioIpDscpPort, prioIpDscpValue }
        ::= { prioIpDscpTable 1 }

PrioIpDscpEntry ::= SEQUENCE
{
    prioIpDscpPort           Integer32,
    prioIpDscpValue          Integer32,
    prioIpDscpCos            Integer32,
    prioIpDscpStatus         EnabledStatus
}

prioIpDscpPort OBJECT-TYPE
        SYNTAX      Integer32
        MAX-ACCESS  not-accessible
        STATUS      current
        DESCRIPTION "The port and the trunk (excluding trunk members) interface of
                     the portTable. The interface identified by a particular value
                     of this index is the same interface as identified by the same
                     value of ifIndex in the IF-MIB."
        ::= { prioIpDscpEntry 1 }

prioIpDscpValue OBJECT-TYPE
        SYNTAX      Integer32 (0..63)
        MAX-ACCESS  not-accessible
        STATUS      current
        DESCRIPTION "Value of IP DSCP as specified in the packet header."
        ::= { prioIpDscpEntry 2 }

prioIpDscpCos OBJECT-TYPE
        SYNTAX      Integer32 (0..7)
        MAX-ACCESS  read-write
        STATUS      current
        DESCRIPTION "Class of Service as defined by dot1dTrafficClassPriority
                     in the P-BRIDGE-MIB. The prioIpDscpValue value in the same
                     table row will be mapped to this Class of Service (CoS).
                     This CoS is then further mapped to the hardware
                     queue according to dot1dTrafficClassTable."
        REFERENCE   "P-BRIDGE-MIB.dot1dPriority.dot1dTrafficClassTable."
        ::= { prioIpDscpEntry 3 }

prioIpDscpStatus OBJECT-TYPE
        SYNTAX      EnabledStatus
        MAX-ACCESS  read-write
        STATUS      current
        DESCRIPTION "The IP DSCP Status. Set this value to enabled(1) to enable
                     the DSCP, set this value to disabled(2) to disable the
                     DSCP."
        ::= { prioIpDscpEntry 4 }

prioIpDscpRestoreDefault OBJECT-TYPE
        SYNTAX      Integer32
        MAX-ACCESS  read-write
        STATUS      current
        DESCRIPTION "Enables the IP DSCP settings of a port to be reset to their
                     defaults. To reset the IP DSCP settings of a port, assign
                     the value of the relevant ifIndex defined by the ifIndex in
                     the IF-MIB. For example, assigning the value 1 will result in
                     the IP DSCP settings of port 1 being restored to their default.
                     0 will always be obtained when reading this variable"
        ::= { priorityMgt 5 }

-- optional
prioIpPortEnableStatus OBJECT-TYPE
        SYNTAX      EnabledStatus
        MAX-ACCESS  read-write
        STATUS      current
        DESCRIPTION "Whether IP Port priority look-up is enabled."
        ::= { priorityMgt 6 }

prioIpPortTable OBJECT-TYPE
        SYNTAX      SEQUENCE OF PrioIpPortEntry
        MAX-ACCESS  not-accessible
        STATUS      current
        DESCRIPTION "Table for IP port priority mapping."
        ::= { priorityMgt 7 }

prioIpPortEntry OBJECT-TYPE
        SYNTAX      PrioIpPortEntry
        MAX-ACCESS  not-accessible
        STATUS      current
        DESCRIPTION "Entry for IP port priority mapping."
        INDEX       { prioIpPortPhysPort,prioIpPortValue }
        ::= { prioIpPortTable 1 }

PrioIpPortEntry ::= SEQUENCE
{
    prioIpPortPhysPort       Integer32,
    prioIpPortValue          Integer32,
    prioIpPortCos            Integer32,
    prioIpPortStatus         ValidStatus
}

prioIpPortPhysPort OBJECT-TYPE
        SYNTAX      Integer32
        MAX-ACCESS  not-accessible
        STATUS      current
        DESCRIPTION "The port or the trunk (excluding trunk member) interface of
                     the portTable. The interface identified by a particular value
                     of this index is the same interface as identified by the same
                     value of ifIndex in the IF-MIB."
        ::= { prioIpPortEntry 1 }

prioIpPortValue OBJECT-TYPE
        SYNTAX      Integer32 (1..65535)
        MAX-ACCESS  not-accessible
        STATUS      current
        DESCRIPTION "IP port for this value."
        ::= { prioIpPortEntry 2 }

prioIpPortCos OBJECT-TYPE
        SYNTAX      Integer32 (0..7)
        MAX-ACCESS  read-create
        STATUS      current
        DESCRIPTION "Class of service for this entry."
        ::= { prioIpPortEntry 3 }

prioIpPortStatus OBJECT-TYPE
        SYNTAX      ValidStatus
        MAX-ACCESS  read-create
        STATUS      current
        DESCRIPTION "Writing this to valid(1) creates an entry.
                     Writing this to invalid(2) destroys an entry."
        ::= { prioIpPortEntry 4 }

-- optional
prioCopy            OBJECT IDENTIFIER ::= { priorityMgt 8 }

prioCopyIpPrec OBJECT-TYPE
        SYNTAX      OCTET STRING
        MAX-ACCESS  read-write
        STATUS      current
        DESCRIPTION "Action to copy IP Precedence settings from
                    a source port to many destination ports.
                    The first four octets represent an integer for
                    the source port in high-to-low (big-endian) order.
                    Starting from the 5th octet is the destination port list
                    in a form described by PortList in the Q-BRIDGE-MIB.
                    Writing this object will perform copy.
                    Reading this object will always get a zero-length
                    octet string."
        ::= { prioCopy 1 }

prioCopyIpDscp OBJECT-TYPE
        SYNTAX      OCTET STRING
        MAX-ACCESS  read-write
        STATUS      current
        DESCRIPTION "Action to copy IP DSCP settings from
                    a source port to many destination ports.
                    The first four octets represent an integer for
                    the source port in high-to-low (big-endian) order.
                    Starting from the 5th octet is the destination port list
                    in a form described by PortList in the Q-BRIDGE-MIB.
                    Writing this object will perform copy.
                    Reading this object will always get a zero-length
                    octet string."
        ::= { prioCopy 2 }

prioCopyIpPort OBJECT-TYPE
        SYNTAX      OCTET STRING
        MAX-ACCESS  read-write
        STATUS      current
        DESCRIPTION "Action to copy IP Port settings from
                    a source port to many destination ports.
                    The first four octets represent an integer for
                    the source port in high-to-low (big-endian) order.
                    Starting from the 5th octet is the destination port list
                    in a form described by PortList in the Q-BRIDGE-MIB.
                    Writing this object will perform copy.
                    Reading this object will always get a zero-length
                    octet string."
        ::= { prioCopy 3 }

prioWrrTable OBJECT-TYPE
        SYNTAX      SEQUENCE OF PrioWrrEntry
        MAX-ACCESS  not-accessible
        STATUS      current
        DESCRIPTION "Table for weighted round robin (WRR)."
        ::= { priorityMgt 9 }

prioWrrEntry OBJECT-TYPE
        SYNTAX      PrioWrrEntry
        MAX-ACCESS  not-accessible
        STATUS      current
        DESCRIPTION "Entry for weighted round robin (WRR)."
        INDEX       { prioWrrTrafficClass }
        ::= { prioWrrTable 1 }

PrioWrrEntry ::= SEQUENCE
{
    prioWrrTrafficClass    Integer32,
    prioWrrWeight          Integer32
}

prioWrrTrafficClass OBJECT-TYPE
        SYNTAX      Integer32 (0..7)
        MAX-ACCESS  not-accessible
        STATUS      current
        DESCRIPTION "Traffic class for this entry, as defined in
                    dot1dTrafficClass in the P-BRIDGE-MIB. The actual
                    maximum depends on the hardware, and is
                    equal to dot1dPortNumTrafficClasses-1."
        REFERENCE "MIB.IETF|P-BRIDGE-MIB.dot1dTrafficClass."
        ::= { prioWrrEntry 1 }

prioWrrWeight OBJECT-TYPE
        SYNTAX      Integer32 (1..255)
        MAX-ACCESS  read-write
        STATUS      current
        DESCRIPTION "Weight for this entry."
        ::= { prioWrrEntry 2 }




-- ACD only
--prioWrrStatus OBJECT-TYPE
--        SYNTAX      EnabledStatus
--        MAX-ACCESS  read-write
--        STATUS      current
--        DESCRIPTION "The global status for the prioWrr."
--        ::= { priorityMgt 10 }

-- NOT ACD
prioQueueMode OBJECT-TYPE
        SYNTAX  INTEGER {
                    wrr(1),
                    strict(2)
                }
        MAX-ACCESS  read-write
        STATUS      current
        DESCRIPTION "The global status for the prioQueue.
                     wrr(1),strict(2)"
        ::= { priorityMgt 10 }

--prioPortTable
prioPortTable OBJECT-TYPE
        SYNTAX      SEQUENCE OF PrioPortEntry
        MAX-ACCESS  not-accessible
        STATUS      current
        DESCRIPTION "Table of prioriy port."
        ::= { priorityMgt 11 }

prioPortEntry OBJECT-TYPE
        SYNTAX      PrioPortEntry
        MAX-ACCESS  not-accessible
        STATUS      current
        DESCRIPTION "A conceptual row of the prioPortTable."
        INDEX       { prioPortIfIndex }
        ::= { prioPortTable 1 }

PrioPortEntry ::= SEQUENCE
{
    prioPortIfIndex           Integer32,
    prioPortQueueMode         INTEGER
}

prioPortIfIndex OBJECT-TYPE
        SYNTAX      Integer32
        MAX-ACCESS  not-accessible
        STATUS      current
        DESCRIPTION "The port interface of the prioPortEntry. The interface
                     identified by a particular value of this index is the
                     same interface as identified by the same value of
                     ifIndex in the IF-MIB."
        ::= { prioPortEntry 1 }

prioPortQueueMode OBJECT-TYPE
        SYNTAX      INTEGER
                    {
                        wrr(1),
                        strict(2)
                    }
        MAX-ACCESS  read-write
        STATUS      current
        DESCRIPTION "The per port status for the prioWrr."
        ::= { prioPortEntry 2 }

--prioWrrPortTable
prioWrrPortTable OBJECT-TYPE
        SYNTAX      SEQUENCE OF PrioWrrPortEntry
        MAX-ACCESS  not-accessible
        STATUS      current
        DESCRIPTION "Table for per port weighted round robin (WRR)."
        ::= { priorityMgt 12 }

prioWrrPortEntry OBJECT-TYPE
        SYNTAX      PrioWrrPortEntry
        MAX-ACCESS  not-accessible
        STATUS      current
        DESCRIPTION "Entry for per port weighted round robin (WRR)."
        INDEX       { prioWrrPortIfIndex,prioWrrPortTrafficClass }
        ::= { prioWrrPortTable 1 }

PrioWrrPortEntry ::= SEQUENCE
{
    prioWrrPortIfIndex         Integer32,
    prioWrrPortTrafficClass    Integer32,
    prioWrrPortWeight          Integer32
}

prioWrrPortIfIndex OBJECT-TYPE
        SYNTAX      Integer32
        MAX-ACCESS  not-accessible
        STATUS      current
        DESCRIPTION "The port interface of the prioWrrPortEntry. The interface
                     identified by a particular value of this index is the
                     same interface as identified by the same value of
                     ifIndex in the IF-MIB."
        ::= { prioWrrPortEntry 1 }

prioWrrPortTrafficClass OBJECT-TYPE
        SYNTAX      Integer32 (0..7)
        MAX-ACCESS  not-accessible
        STATUS      current
        DESCRIPTION "Traffic class for this entry, as defined in
                    dot1dTrafficClass in the P-BRIDGE-MIB. The actual
                    maximum depends on the hardware, and is
                    equal to dot1dPortNumTrafficClasses-1."
        REFERENCE "MIB.IETF|Q-BRIDGE-MIB.dot1dTrafficClass."
        ::= { prioWrrPortEntry 2 }

prioWrrPortWeight OBJECT-TYPE
        SYNTAX      Integer32 (1..255)
        MAX-ACCESS  read-write
        STATUS      current
        DESCRIPTION "Weight for this entry."
        ::= { prioWrrPortEntry 3 }

-- prioWrrInternalPortTable

prioWrrInternalPortTable OBJECT-TYPE
        SYNTAX      SEQUENCE OF PrioWrrInternalPortEntry
        MAX-ACCESS  not-accessible
        STATUS      current
        DESCRIPTION "Weighted round robin (WRR) table for internal HG port."
        ::= { priorityMgt 14 }

prioWrrInternalPortEntry OBJECT-TYPE
        SYNTAX      PrioWrrInternalPortEntry
        MAX-ACCESS  not-accessible
        STATUS      current
        DESCRIPTION "Weighted round robin (WRR) entry for internal HG port."
        INDEX       { prioWrrInternalPortTrafficClass }
        ::= { prioWrrInternalPortTable 1 }

PrioWrrInternalPortEntry ::= SEQUENCE
{
    prioWrrInternalPortTrafficClass    Integer32,
    prioWrrInternalPortWeight          Integer32
}

prioWrrInternalPortTrafficClass OBJECT-TYPE
        SYNTAX      Integer32 (0..7)
        MAX-ACCESS  not-accessible
        STATUS      current
        DESCRIPTION "Traffic class for this entry, as defined in
                    dot1dTrafficClass in the P-BRIDGE-MIB. The actual
                    maximum depends on the hardware, and is
                    equal to dot1dPortNumTrafficClasses-1."
        REFERENCE "MIB.IETF|Q-BRIDGE-MIB.dot1dTrafficClass."
        ::= { prioWrrInternalPortEntry 1 }

prioWrrInternalPortWeight OBJECT-TYPE
        SYNTAX      Integer32 (0..15)
        MAX-ACCESS  read-write
        STATUS      current
        DESCRIPTION "Weight for this entry. The vlaue 0 means that this queue uses strict mode."
        ::= { prioWrrInternalPortEntry 2 }

--prioAclToCosTable
prioAclToCosTable OBJECT-TYPE
        SYNTAX      SEQUENCE OF PrioAclToCosEntry
        MAX-ACCESS  not-accessible
        STATUS      current
        DESCRIPTION "Table for ACL to CoS Mapping."
        ::= { priorityMgt 13 }

prioAclToCosEntry OBJECT-TYPE
        SYNTAX      PrioAclToCosEntry
        MAX-ACCESS  not-accessible
        STATUS      current
        DESCRIPTION "Entry for ACL to CoS Mapping."
        INDEX       { prioAclToCosIfIndex }
        ::= { prioAclToCosTable 1 }

PrioAclToCosEntry ::= SEQUENCE
{
    prioAclToCosIfIndex    Integer32,
    prioAclToCosIpAclName  DisplayString,
    prioAclToCosMacAclName DisplayString,
    prioAclToIpCosValue      Integer32,
    prioAclToMacCosValue      Integer32
}

prioAclToCosIfIndex OBJECT-TYPE
        SYNTAX      Integer32
        MAX-ACCESS  not-accessible
        STATUS      current
        DESCRIPTION "The port interface of the prioAclToCosEntry. The interface
                     identified by a particular value of this index is the
                     same interface as identified by the same value of
                     ifIndex in the IF-MIB."
        ::= { prioAclToCosEntry 1 }

prioAclToCosIpAclName OBJECT-TYPE
        SYNTAX      DisplayString (SIZE(0..16))
        MAX-ACCESS  read-write
        STATUS      current
        DESCRIPTION "The name of an IP ACL. Within a feature, a unique
                    name is used to identify the list to
                    which the entry belongs in the device."
        ::= { prioAclToCosEntry 2 }

prioAclToCosMacAclName OBJECT-TYPE
        SYNTAX      DisplayString (SIZE(0..16))
        MAX-ACCESS  read-write
        STATUS      current
        DESCRIPTION "The name of an MAC ACL. Within a feature a unique
                    name is used to identify the list to
                    which the entry belongs in the device."
        ::= { prioAclToCosEntry 3 }

prioAclToIpCosValue OBJECT-TYPE
        SYNTAX      Integer32 (0..7)
        MAX-ACCESS  read-write
        STATUS      current
        DESCRIPTION "IP CoS for this entry."
        ::= { prioAclToCosEntry 4 }

prioAclToMacCosValue OBJECT-TYPE
        SYNTAX      Integer32 (0..7)
        MAX-ACCESS  read-write
        STATUS      current
        DESCRIPTION "MAC CoS for this entry."
        ::= { prioAclToCosEntry 5 }

--
-- trapDestMgt
--

-- Management for SNMP traps and trap destinations.

trapDestTable  OBJECT-TYPE
    SYNTAX     SEQUENCE OF TrapDestEntry
    MAX-ACCESS not-accessible
    STATUS     current
    DESCRIPTION
        "A list of trap destination entries."
    REFERENCE "RMON2-MIB, mib2(1).rmon(16).probeConfig(19).trapDestTable(13)."
    ::= { trapDestMgt 1 }

trapDestEntry  OBJECT-TYPE
    SYNTAX     TrapDestEntry
    MAX-ACCESS not-accessible
    STATUS     current
    DESCRIPTION  "A destination entry describes the destination IP address,
                  the community string, and SNMP version to use when sending
                  a trap."
    INDEX { trapDestAddress }
    ::= { trapDestTable 1 }

TrapDestEntry ::= SEQUENCE {
    trapDestAddress             IpAddress,
    trapDestCommunity           OCTET STRING,
    trapDestStatus              ValidStatus,
    trapDestVersion             INTEGER,
    trapDestUdpPort             Integer32
}

trapDestAddress  OBJECT-TYPE
    SYNTAX     IpAddress
    MAX-ACCESS not-accessible
    STATUS     current
    DESCRIPTION
        "The address to send traps."
    ::= { trapDestEntry 1 }

trapDestCommunity  OBJECT-TYPE
    SYNTAX     OCTET STRING (SIZE(0..32))
    MAX-ACCESS read-create
    STATUS     current
    DESCRIPTION
        "A community to which this destination address belongs."
    ::= { trapDestEntry 2 }

trapDestStatus  OBJECT-TYPE
    SYNTAX     ValidStatus
    MAX-ACCESS read-create
    STATUS     current
    DESCRIPTION
        "Setting this to valid(1) creates an entry.
         Setting this to invalid(2) destroys an entry."
    ::= { trapDestEntry 3 }

trapDestVersion OBJECT-TYPE
    SYNTAX     INTEGER
               {
                   version1(1),
                   version2(2)
               }
    MAX-ACCESS read-create
    STATUS     current
    DESCRIPTION "Determines the version of the trap that is to be sent to the
                 trap receiver. If the value is 1, then an SNMP version 1 trap
                 is sent and if the value is 2, an SNMP version 2 trap is
                 sent."
    ::= { trapDestEntry 4}

trapDestUdpPort OBJECT-TYPE
    SYNTAX      Integer32 (1..65535)
    MAX-ACCESS  read-create
    STATUS      current
    DESCRIPTION "Determines the UDP port number of the trap that is to be sent to the
                 trap Receiver."
    DEFVAL      { 162 }
    ::= { trapDestEntry 5}

-- trapVar is for binding variables for traps, there is no value when
-- no trap is sent.
trapVar OBJECT IDENTIFIER ::= { trapDestMgt 2 }

-- FTTH only
trapRestartType OBJECT-TYPE
     SYNTAX    INTEGER
                   {
                     none(1),
                     command(2),
                     powerOn(3)
                   }
     MAX-ACCESS accessible-for-notify
     STATUS     current
     DESCRIPTION
         "This variable indicates the restart type for trap variable binding.
          command(1) means restarting through cli/snmp/web, powerOn(2) means
          restarting through A/C Power. none(1) will always be obtained when
          reading this variable."
     ::= { trapVar 1 }


trapSensitivityEventType OBJECT-TYPE
     SYNTAX   INTEGER
              {
                 none(1),
                 minorFail(2),
                 majorFail(3),
                 clear(4)
              }
     MAX-ACCESS accessible-for-notify
     STATUS     current
     DESCRIPTION
         " This variable is for trap binding, when an alarm sensitivity trap
           is sent, it will bind this variable to the trap receiver as the 3rd parameter
           to indicate the type of failure. none(1) will always be obtained when
          reading this variable."
     ::= { trapVar 2 }

trapDiagnosisResult OBJECT-TYPE
     SYNTAX      Integer32
     MAX-ACCESS  accessible-for-notify
     STATUS      current
     DESCRIPTION "This variable is for trap binding, When a diagnosis result
                  trap is sent, it will bind this variable to the trap receiver,
                  0 means good, other values mean the NG test number. When read,
                  it always return 0."
     ::= { trapVar 3 }

trapIpFilterRejectMode OBJECT-TYPE
     SYNTAX      INTEGER
                 {
                     web(1),
                     snmp(2),
                     telnet(3)
                 }
     MAX-ACCESS  accessible-for-notify
     STATUS      current
     DESCRIPTION "This variable is for trap var binding,
                  indicated the ipfilter reject mode.
                  web(1),
                  snmp(2),
                  telnet(3)."
     ::= { trapVar 6 }

trapIpFilterRejectIp OBJECT-TYPE
     SYNTAX      IpAddress
     MAX-ACCESS  accessible-for-notify
     STATUS      current
     DESCRIPTION "This variable is for trap var binding,
                 indicating the IP address that rejected by the ipfilter."
     ::= { trapVar 7 }


trapVarMibObjId OBJECT-TYPE
    SYNTAX     OBJECT IDENTIFIER
    MAX-ACCESS accessible-for-notify
    STATUS     current
    DESCRIPTION
            "Object ID of the mib variable."
    ::= { trapVar 8 }

trapVarTcnReason OBJECT-TYPE
    SYNTAX      INTEGER
                {
                 pushButton(1),
                 stackingLinkDown(2),
                 stackingLinkUp(3),
                 hbtTimeout(4),
                 hbtError(5),
                 slave(6)
                }
    MAX-ACCESS  accessible-for-notify
    STATUS      current
    DESCRIPTION "The variable represents the function of TCN:
                 pushButton(1): Enables the unit as the Master unit in the stack.
                 stackingLinkDown(2): Master stacking link is down.
                 stackingLinkUp(3): Master stacking link is up.
                 hbtTimeout(4): Control packet sent from the Master through all units has timed-out.
                 hbtError(5): Control packet sent from the Master through all units was received with errors.
                 slave(6): A Slave unit notifies the Master unit of a topology change."
    ::= { trapVar 9 }

trapVarMacAddr OBJECT-TYPE
    SYNTAX     MacAddress
    MAX-ACCESS accessible-for-notify
    STATUS     current
    DESCRIPTION
            "The variable binding for mac address type."
    ::= { trapVar 10 }

trapVarLoginUserName OBJECT-TYPE
     SYNTAX      DisplayString(SIZE(1..8))
     MAX-ACCESS  accessible-for-notify
     STATUS      current
     DESCRIPTION "The name of the user who logs into the switch."
     ::= { trapVar 11 }

trapVarLoginMethod OBJECT-TYPE
     SYNTAX      INTEGER
                 {
                     web(1),
                     snmp(2),
                     telnet(3),
                     console(4)
                 }
     MAX-ACCESS  accessible-for-notify
     STATUS      current
     DESCRIPTION "The method by which the user logs in to control the
                  switch."
     ::= { trapVar 12 }

trapVarLoginIPAddress OBJECT-TYPE
     SYNTAX      IpAddress
     MAX-ACCESS  accessible-for-notify
     STATUS      current
     DESCRIPTION "The IP address from which the user logs into the switch."
     ::= { trapVar 13 }

trapVarLoginTime OBJECT-TYPE
     SYNTAX      DisplayString
     MAX-ACCESS  accessible-for-notify
     STATUS      current
     DESCRIPTION "The date and time when the user logs into the switch."
     ::= { trapVar 14 }

trapVarLoginInetAddressType OBJECT-TYPE
     SYNTAX      InetAddressType
     MAX-ACCESS  accessible-for-notify
     STATUS      current
     DESCRIPTION "The address type of the address associated with this agent.
                  Only IPv4 and IPv6 types are supported."
     ::= { trapVar 15 }

trapVarLoginInetAddress OBJECT-TYPE
     SYNTAX      InetAddress
     MAX-ACCESS  accessible-for-notify
     STATUS      current
     DESCRIPTION "The IP address from which the user logs into the switch."
     ::= { trapVar 16 }

trapEnableMgt OBJECT IDENTIFIER ::= { trapDestMgt 3 }

trapEnableAll OBJECT-TYPE
     SYNTAX      EnabledStatus
     MAX-ACCESS  read-write
     STATUS      current
     DESCRIPTION "Set this variable to disabled(2) to disable all traps;
                  set this variable to enabled(1) to enable all traps."
     ::= { trapEnableMgt 1 }

trapBladeEnableStatus OBJECT-TYPE
     SYNTAX          EnabledStatus
     MAX-ACCESS   read-write
     STATUS       current
     DESCRIPTION " Set enabled(1) to enable the trap of the blade number,
                   the current blade number is located in the bladeIndex."
     ::= { trapEnableMgt 2 }

trapEnablePortTable  OBJECT-TYPE
    SYNTAX     SEQUENCE OF TrapEnablePortEntry
    MAX-ACCESS not-accessible
    STATUS     current
    DESCRIPTION
        "This table is used to defined which ports are enabled for traps."
    ::= { trapEnableMgt 3 }

trapEnablePortEntry  OBJECT-TYPE
    SYNTAX     TrapEnablePortEntry
    MAX-ACCESS not-accessible
    STATUS     current
    DESCRIPTION
        "A conceptual row for ftthTrapEnablePortTable."
    INDEX { trapEnablePortIfIndex }
    ::= { trapEnablePortTable 1 }

TrapEnablePortEntry ::= SEQUENCE
{
    trapEnablePortIfIndex       Integer32,
    trapEnablePortStatus        EnabledStatus,
    trapEnableLogStatus     EnabledStatus
}

trapEnablePortIfIndex  OBJECT-TYPE
    SYNTAX     Integer32
    MAX-ACCESS not-accessible
    STATUS     current
    DESCRIPTION
        "This is defined as the ifIndex in IF-MIB."
    ::= { trapEnablePortEntry 1 }

trapEnablePortStatus  OBJECT-TYPE
    SYNTAX     EnabledStatus
    MAX-ACCESS read-write
    STATUS     current
    DESCRIPTION
        "Whether the trap for a port is enabled."
    ::= { trapEnablePortEntry 2 }

trapEnableLogStatus  OBJECT-TYPE
    SYNTAX     EnabledStatus
    MAX-ACCESS read-write
    STATUS     current
    DESCRIPTION
        "Whether the trap for a log is enabled."
    ::= { trapEnablePortEntry 3 }

trapEnableAllAlarm OBJECT-TYPE
    SYNTAX     EnabledStatus
    MAX-ACCESS read-write
    STATUS     current
    DESCRIPTION "Whether the trap for all alarms is enabled."
    ::= { trapEnableMgt 4 }

trapEnableAlarmSensitivity OBJECT-TYPE
     SYNTAX    EnabledStatus
     MAX-ACCESS read-write
     STATUS     current
     DESCRIPTION "Whether the alarm sensitivity is enabled."
    ::= { trapEnableMgt 5 }

trapEnablePortSecIntrusion OBJECT-TYPE
        SYNTAX      EnabledStatus
        MAX-ACCESS  read-write
        STATUS      current
        DESCRIPTION "Whether the port security intrusion trap is enabled."
        ::= { trapEnableMgt 6  }

-- trapDestHostTable

trapDestHostTable  OBJECT-TYPE
    SYNTAX     SEQUENCE OF TrapDestHostEntry
    MAX-ACCESS not-accessible
    STATUS     current
    DESCRIPTION
        "A list of trap destination entries."
    ::= { trapDestMgt 4 }

trapDestHostEntry    OBJECT-TYPE
    SYNTAX       TrapDestHostEntry
    MAX-ACCESS   not-accessible
    STATUS       current
    DESCRIPTION  "A destination entry describes the destination host,
                  community string, and SNMP version to use when sending
                  a trap."
    INDEX { trapDestHostName }
    ::= { trapDestHostTable 1 }

TrapDestHostEntry ::= SEQUENCE {
    trapDestHostName                DisplayString,
    trapDestHostCommunity           OCTET STRING,
    trapDestHostStatus              ValidStatus,
    trapDestHostVersion             INTEGER
}

trapDestHostName   OBJECT-TYPE
    SYNTAX     DisplayString(SIZE(0..255))
    MAX-ACCESS not-accessible
    STATUS     current
    DESCRIPTION
        "IP address or domain name of the destination host to send traps."
    ::= { trapDestHostEntry 1 }

trapDestHostCommunity  OBJECT-TYPE
    SYNTAX     OCTET STRING (SIZE(0..127))
    MAX-ACCESS read-create
    STATUS     current
    DESCRIPTION
        "A community to which this destination address belongs."
    ::= { trapDestHostEntry 2 }

trapDestHostVersion OBJECT-TYPE
    SYNTAX      INTEGER
                {
                   version1(1),
                   version2(2)
                }
    MAX-ACCESS   read-create
    STATUS       current
    DESCRIPTION "Determines the version of the trap that is to be sent to the
                 trap receiver. If the value is 1, then an SNMP version 1 trap
                 is sent and if the value is 2, an SNMP version 2 trap is
                 sent."
    ::= { trapDestHostEntry 3}

trapDestHostStatus  OBJECT-TYPE
    SYNTAX     ValidStatus
    MAX-ACCESS read-create
    STATUS     current
    DESCRIPTION
        "Setting this to valid(1) creates an entry.
         Setting this to invalid(2) destroys an entry."
    ::= { trapDestHostEntry 4 }

--
-- AlarmMgt
--
alarmMgt OBJECT IDENTIFIER ::= { trapDestMgt 5 }
alarmMajorType      OBJECT-TYPE
    SYNTAX      INTEGER
                {
                    allFeLinkDown(1),
                    allGeLinkDown(2),
                    allFanFailure(3),
                    powerModuleFailure(4),
                    wrongPowerModuleSet(5),
                    thermalDetectorOverHeating(6),
                    fanFailure(7)
                }
    MAX-ACCESS  accessible-for-notify
    STATUS      current
    DESCRIPTION "The parameter indicates which event triggers the trap."
    ::= { alarmMgt 1 }

alarmMajorStatus    OBJECT-TYPE
    SYNTAX      BITS
                {
                    allFeLinkDown(0),
                    allGeLinkDown(1),
                    allFanFailure(2),
                    powerModuleFail(3),
                    wrongPowerModuleSet(4),
                    thermalDetectorOverHeating(5),
                    fanFailure(6)
                }
    MAX-ACCESS  read-only
    STATUS      current
    DESCRIPTION "The parameter indicates which event triggers the trap."
    ::= { alarmMgt 2 }

alarmMinorType      OBJECT-TYPE
    SYNTAX      INTEGER
                {
                    feLinkDown(1),
                    geLinkDown(2),
                    fanFailure(3),
                    thermalDetectorOverHeating(4),
                    thermalDetectorOverCooling(5),
                    powerSupplyUnitAMissing(6),
                    powerSupplyUnitBMissing(7)
                }
    MAX-ACCESS  accessible-for-notify
    STATUS      current
    DESCRIPTION "The parameter indicates which event triggers the trap."
    ::= { alarmMgt 3 }

alarmMinorStatus    OBJECT-TYPE
    SYNTAX      BITS
                {
                    feLinkDown(0),
                    geLinkDown(1),
                    fanFailure(2),
                    thermalDetectorOverHeating(3),
                    thermalDetectorOverCooling(4),
                    powerSupplyUnitAMissing(5),
                    powerSupplyUnitBMissing(6)
                }
    MAX-ACCESS  read-only
    STATUS      current
    DESCRIPTION "The parameter indicates which event triggers the trap."
    ::= { alarmMgt 4 }

alarmMajorRecoveryType    OBJECT-TYPE
    SYNTAX      INTEGER
                {
                 powerModuleRecovery(1),
                 wrongPowerModuleSetRecovery(2),
                 thermalDetectorOverHeatingRecovery(3),
                 fanRecovery(4)
                }
    MAX-ACCESS  accessible-for-notify
    STATUS      current
    DESCRIPTION "The parameter indicates which event triggers the trap."
    ::= { alarmMgt 5 }

alarmMajorRecoveryStatus    OBJECT-TYPE
    SYNTAX      BITS
                {
                 powerModuleRecovery(0),
                 wrongPowerModuleSetRecovery(1),
                 thermalDetectorOverHeatingRecovery(2),
                 fanRecovery(3)
                }
    MAX-ACCESS  read-only
    STATUS      current
    DESCRIPTION "The parameter indicates which event triggers the trap."
    ::= { alarmMgt 6 }

-- [Terawave]

alarmInputType      OBJECT-TYPE
    SYNTAX      INTEGER
                {
                    alarmInputType1(1),
                    alarmInputType2(2),
                    alarmInputType3(3),
                    alarmInputType4(4)
                }
    MAX-ACCESS  accessible-for-notify
    STATUS      current
    DESCRIPTION "The parameter indicates the alarm input type which triggers the trap."
    ::= { alarmMgt 7 }

-- [Terawave]

alarmInputStatus    OBJECT-TYPE
    SYNTAX      BITS
                {
                    alarmInputType1(0),
                    alarmInputType2(1),
                    alarmInputType3(2),
                    alarmInputType4(3)
                }
    MAX-ACCESS  read-only
    STATUS      current
    DESCRIPTION "The parameter indicates the alarm input status."
    ::= { alarmMgt 8 }

--
-- vdslMgt
--


-- Management for Very high data rate Digital Subscriber Line (VDSL).

-- Define VDSL Port Config table
-- Module Identity : vdslMIBObjects/vdslConfigTable
--

    vdslConfigTable OBJECT-TYPE
        SYNTAX     SEQUENCE OF VDSLConfigEntry
        MAX-ACCESS not-accessible
        STATUS     current
        DESCRIPTION "Config Paramter for each VDSL port."
        ::= { vdslMgt 1 }

    vdslConfigEntry OBJECT-TYPE
        SYNTAX     VDSLConfigEntry
        MAX-ACCESS not-accessible
        STATUS     current
        DESCRIPTION "The entry of config table."
        INDEX       { vdslPortIndex }
        ::= { vdslConfigTable 1 }

    VDSLConfigEntry ::=
        SEQUENCE {
            vdslPortIndex                       InterfaceIndex,
            vdslPortActive                      INTEGER,
            vdslPortRDL                         INTEGER,
            vdslPortProfile                     INTEGER
        }

    vdslPortIndex OBJECT-TYPE
        SYNTAX      InterfaceIndex
        MAX-ACCESS  not-accessible
        STATUS      current
        DESCRIPTION "An index value that uniquely identifies an
                   interface to a VDSL port. The
                   interface identified by a particular value of
                   this index is the same interface as identified
                   by the same value of ifIndex."
        ::= { vdslConfigEntry 1 }

    vdslPortActive OBJECT-TYPE
        SYNTAX      INTEGER
                    {
                        active(1),
                        deactive(2)
                    }
        MAX-ACCESS  read-write
        STATUS      current
        DESCRIPTION "The active status of the VDSL port.
                     Set 1 to activate the port. Set 2 to
                     deactivate the port."
        ::= { vdslConfigEntry 2 }

    vdslPortRDL OBJECT-TYPE
        SYNTAX      INTEGER
                      {

                        enable(1),
                        disable(2)
                       }
        MAX-ACCESS  read-write
        STATUS      current
        DESCRIPTION "The status of RDL,
                     set 1 to turn on RDL, set 2 to
                     turn off RDL."
        ::= { vdslConfigEntry 3 }

    vdslPortProfile OBJECT-TYPE
        SYNTAX      INTEGER
                      {

                        default(0),
                        efm-5(1),
                        efm-10(2),
                        efm-15(3),
                        public-ansi(4),
                        public-etsi(5),
                        efm-5LL(6),
                        efm-10LL(7),
                        efm-15LL(8),
                        public-ansiLL(9),
                        public-etsiLL(10),
                        efm-15-3LL(11),
                        efm-15-2LL(12),
                        efm-15-1LL(13),
                        efm-10-2LL(14),
                        user-1(15),
                        user-2(16)
                     }
        MAX-ACCESS  read-write
        STATUS      current
        DESCRIPTION "The Profile ID of the port, starts from 0.
                     Change this value to change to different VDSL
                     line rate speeds, the number is defined
                     as: default=0, efm-5=1, efm-10=2, efm-15=3,
                     public-ansi=4, public-etsi=5, efm-5LL =6,
                     efm-10LL=7, efm-15LL=8, public-ansiLL=9,
                     public-etsiLL=10, efm-15-3LL=11, efm-152LL=12,
                     efm-15-1LL=13, efm-10-2LL=14, user-1=15, user-2=16.
                     user-1 and user-2 are user defined profiles, we
                     can config these in the vdslPortUserProfileTable."
        ::= { vdslConfigEntry 4 }
--
-- Define VDSL Link General Status table
-- Module Identity : vdslMIBObjects/vdslGenStatusTable
--

    vdslGenStatusTable OBJECT-TYPE
        SYNTAX     SEQUENCE OF VDSLGenStatusEntry
        MAX-ACCESS not-accessible
        STATUS     current
        DESCRIPTION "VDSL link general status."
        ::= { vdslMgt 2 }

    vdslGenStatusEntry  OBJECT-TYPE
        SYNTAX     VDSLGenStatusEntry
        MAX-ACCESS not-accessible
        STATUS     current
        DESCRIPTION "The entry of general status table."
        INDEX       { vdslGenStatusPortIndex }
        ::= { vdslGenStatusTable 1 }

    VDSLGenStatusEntry ::=
        SEQUENCE {
            vdslGenStatusPortIndex              InterfaceIndex,
            vdslGenStatusLink                   Counter32,
            vdslGenStatusFailCnt                Counter32
        }

    vdslGenStatusPortIndex OBJECT-TYPE
        SYNTAX      InterfaceIndex
        MAX-ACCESS  not-accessible
        STATUS      current
        DESCRIPTION "An index value that uniquely identifies an
                   interface to a VDSL port. The
                   interface identified by a particular value of
                   this index is the same interface as that identified
                   by the same value of ifIndex."
        ::= { vdslGenStatusEntry 1 }

    vdslGenStatusLink OBJECT-TYPE
        SYNTAX      Counter32
        MAX-ACCESS  read-only
        STATUS      current
        DESCRIPTION "If 1 means link up, 0 means link down."
        ::= { vdslGenStatusEntry 2 }

    vdslGenStatusFailCnt OBJECT-TYPE
        SYNTAX      Counter32
        MAX-ACCESS  read-only
        STATUS      current
        DESCRIPTION "Link fail count."
        ::= { vdslGenStatusEntry 3 }

--
-- Define VDSL link PMD Status table
-- Module Identity : vdslMIBObjects/vdslPMDStatusTable
--

    vdslPMDStatusTable OBJECT-TYPE
        SYNTAX     SEQUENCE OF VDSLPMDStatusEntry
        MAX-ACCESS not-accessible
        STATUS     current
        DESCRIPTION "VDSL Link PMD Status."
        ::= { vdslMgt 3 }

    vdslPMDStatusEntry  OBJECT-TYPE
        SYNTAX     VDSLPMDStatusEntry
        MAX-ACCESS not-accessible
        STATUS     current
        DESCRIPTION "The entry of general status table."
        INDEX       { vdslPMDStatusPortIndex }
        ::= { vdslPMDStatusTable 1 }

    VDSLPMDStatusEntry ::=
        SEQUENCE {
            vdslPMDStatusPortIndex              InterfaceIndex,
            vdslPMDStatusSNR                    Integer32,
            vdslPMDStatusDSRate                Counter32,
            vdslPMDStatusUSRate                Counter32,
            vdslPMDStatusLocalPwr               Integer32,
            vdslPMDStatusRemotePwr              Integer32
        }

    vdslPMDStatusPortIndex OBJECT-TYPE
        SYNTAX      InterfaceIndex
        MAX-ACCESS  not-accessible
        STATUS      current
        DESCRIPTION "An index value that uniquely identifies a
                   interface to a VDSL port. The interface identified by a
                   particular value of this index is the same interface as identified
                   by the same value of the ifIndex."
        ::= { vdslPMDStatusEntry 1 }

    vdslPMDStatusSNR OBJECT-TYPE
        SYNTAX      Integer32
        MAX-ACCESS  read-only
        STATUS      current
        DESCRIPTION "SNR of the link.
                     Divide by 100 to get the real
                     floating value of SNR (dB)."
        ::= { vdslPMDStatusEntry 2 }

    vdslPMDStatusDSRate OBJECT-TYPE
        SYNTAX      Counter32
        MAX-ACCESS  read-only
        STATUS      current
        DESCRIPTION "Downstream Line Speed Rate.
                     Divide by 100 to get the real
                     floating rate value(Mbps)."
        ::= { vdslPMDStatusEntry 3 }

    vdslPMDStatusUSRate OBJECT-TYPE
        SYNTAX      Counter32
        MAX-ACCESS  read-only
        STATUS      current
        DESCRIPTION "Upstream Line Speed Rate.
                     Divide by 100 to get the real
                     floating rate value(Mbps)."
        ::= { vdslPMDStatusEntry 4 }

    vdslPMDStatusLocalPwr OBJECT-TYPE
        SYNTAX      Integer32
        MAX-ACCESS  read-only
        STATUS      current
        DESCRIPTION "Local Transmit Power level.
                     Divide by 100 to get the real
                     floating value of power level (dBm/Hz)."
        ::= { vdslPMDStatusEntry 5 }

    vdslPMDStatusRemotePwr OBJECT-TYPE
        SYNTAX      Integer32
        MAX-ACCESS  read-only
        STATUS      current
        DESCRIPTION "Remote Transmit Power level.
                     Divide by 100 to get the real
                     floating value of power level (dBm/Hz)."
        ::= { vdslPMDStatusEntry 6 }

--
-- Define VDSL link PMS-TC Status table
-- Module Identity : vdslMIBObjects/vdslPMS_TC_StatusTable
--

    vdslPMSTCStatusTable OBJECT-TYPE
        SYNTAX     SEQUENCE OF VDSLPMSTCStatusEntry
        MAX-ACCESS not-accessible
        STATUS     current
        DESCRIPTION "VDSL link PMS-TC status."
        ::= { vdslMgt 4 }

    vdslPMSTCStatusEntry  OBJECT-TYPE
        SYNTAX     VDSLPMSTCStatusEntry
        MAX-ACCESS not-accessible
        STATUS     current
        DESCRIPTION "The entry of PMS-TC status table."
        INDEX       { vdslPMSTCStatusPortIndex }
        ::= { vdslPMSTCStatusTable 1 }

    VDSLPMSTCStatusEntry ::=
        SEQUENCE {
            vdslPMSTCStatusPortIndex         InterfaceIndex,
            vdslPMSTCStatusDSRSErr           Counter32,
            vdslPMSTCStatusUSRSErr           Counter32,
            vdslPMSTCStatusLocalMRX          Counter32,
            vdslPMSTCStatusRemoteMRX         Counter32
        }

    vdslPMSTCStatusPortIndex OBJECT-TYPE
        SYNTAX      InterfaceIndex
        MAX-ACCESS  not-accessible
        STATUS      current
        DESCRIPTION "An index value that uniquely identifies an
                   interface to a VDSL port. The
                   interface identified by a particular value of
                   this index is the same interface as identified
                   by the same value of the ifIndex."
        ::= { vdslPMSTCStatusEntry 1 }

    vdslPMSTCStatusDSRSErr OBJECT-TYPE
        SYNTAX      Counter32
        MAX-ACCESS  read-only
        STATUS      current
        DESCRIPTION "Downstream Reed-Solomon Errors."
        ::= { vdslPMSTCStatusEntry 2 }

    vdslPMSTCStatusUSRSErr OBJECT-TYPE
        SYNTAX      Counter32
        MAX-ACCESS  read-only
        STATUS      current
        DESCRIPTION "Upstream Reed-Solomon Errors."
        ::= { vdslPMSTCStatusEntry 3 }

    vdslPMSTCStatusLocalMRX OBJECT-TYPE
        SYNTAX      Counter32
        MAX-ACCESS  read-only
        STATUS      current
        DESCRIPTION "Local Receive Interleaver Depth."
        ::= { vdslPMSTCStatusEntry 4 }

    vdslPMSTCStatusRemoteMRX OBJECT-TYPE
        SYNTAX      Counter32
        MAX-ACCESS  read-only
        STATUS      current
        DESCRIPTION "Remote Receive Interleaver Depth."
        ::= { vdslPMSTCStatusEntry 5 }

--
-- Define VdslPortUserProfileTable
-- Module Identity : vdslMIBObjectsVdslPortUserProfileTable
--
    vdslPortUserProfileTable OBJECT-TYPE
        SYNTAX     SEQUENCE OF VdslPortUserProfileEntry
        MAX-ACCESS not-accessible
        STATUS     current
        DESCRIPTION "This table is used for the user to defined the VdslPortProfile
                     in vdslConfigTable.vdslPortFile."
        ::= { vdslMgt 5 }

    vdslPortUserProfileEntry  OBJECT-TYPE
        SYNTAX     VdslPortUserProfileEntry
        MAX-ACCESS not-accessible
        STATUS     current
        DESCRIPTION "The VdslPortUserProfile entry."
        INDEX       { vdslPortUserProfileIndex }
        ::= { vdslPortUserProfileTable 1 }

    VdslPortUserProfileEntry ::=
        SEQUENCE {
            vdslPortUserProfileIndex         INTEGER,
            vdslPortUserProfileDownlink      Integer32,
            vdslPortUserProfileUplink        Integer32,
            vdslPortUserProfileInterleave    Integer32
        }

    vdslPortUserProfileIndex OBJECT-TYPE
        SYNTAX INTEGER
                      {
                       user-1(1),
                       user-2(2)
                      }
        MAX-ACCESS not-accessible
        STATUS     current
        DESCRIPTION "This index represent the user-defined profile defined in
                    vdslConfigTable, whether it is user-1(1) or user-2(2),
                    1 stand for user-1(1), 2 stand for user-2(2)."
        ::= { vdslPortUserProfileEntry 1 }

    vdslPortUserProfileDownlink OBJECT-TYPE
        SYNTAX Integer32(1..15)
        MAX-ACCESS read-write
        STATUS     current
        DESCRIPTION "In vdslPortProfile, there are 2 user defined profiles, user-1(15)
                    and user-2(16), This variable is used to specify the ProfileDownlink
                    of the corresponding user-defined profile."
        ::= { vdslPortUserProfileEntry 2 }

    vdslPortUserProfileUplink OBJECT-TYPE
        SYNTAX Integer32(1..15)
        MAX-ACCESS read-write
        STATUS     current
        DESCRIPTION "In vdslPortProfile, there are 2 user defined profiles, user-1(15)
                    and user-2(16). This variable is used to specify the ProfileUplink
                    of the corresponding user-defined profile."
        ::= { vdslPortUserProfileEntry 3 }

    vdslPortUserProfileInterleave OBJECT-TYPE
        SYNTAX Integer32(0..16)
        MAX-ACCESS read-write
        STATUS     current
        DESCRIPTION "In vdslPortProfile, there are 2 user defined profiles, user-1(15)
                    and user-2(16), This variable is used to specify the ProfileInterleave
                    of the corresponding user-defined profile. Note: The possible read-
                    out values are 0,2,16. The possible write values are 2 and 16."
        ::= { vdslPortUserProfileEntry 4 }

--
-- vdslLoopSpeedTestTable
--

    vdslLoopSpeedTestTable OBJECT-TYPE
        SYNTAX     SEQUENCE OF VdslLoopSpeedTestEntry
        MAX-ACCESS not-accessible
        STATUS     current
        DESCRIPTION "This table is for loop speed test."
        ::= { vdslMgt 6 }

    vdslLoopSpeedTestEntry  OBJECT-TYPE
        SYNTAX     VdslLoopSpeedTestEntry
        MAX-ACCESS not-accessible
        STATUS     current
        DESCRIPTION "The entry of vdslLoopSpeedTest Table."
        INDEX       { ifIndex }
        ::= { vdslLoopSpeedTestTable 1 }

    VdslLoopSpeedTestEntry ::=
        SEQUENCE {
        vdslLoopSpeedTestAction       INTEGER,
            vdslLoopSpeedTestDSRate               Counter32,
            vdslLoopSpeedTestUSRate               Counter32,
            vdslLoopSpeedTestResult               INTEGER
        }

     vdslLoopSpeedTestAction OBJECT-TYPE
        SYNTAX    INTEGER
                 {
                    loopSpeedTest(1),
                    noLoopSpeedTest(2)
                 }
        MAX-ACCESS read-write
        STATUS      current
        DESCRIPTION "Set to loopSpeedTest(1) to perform loopspeed test.
                     When read, returns noLoopSpeedTest(2) when no loopspeed test
                     is being performed."
        ::= { vdslLoopSpeedTestEntry 1 }

      vdslLoopSpeedTestDSRate OBJECT-TYPE
        SYNTAX      Counter32
        MAX-ACCESS read-only
        STATUS      current
        DESCRIPTION "The result of the last loopspeed test, indicating the
                     downnstream speed rate, should be divided by 100 to get
                     the actual value."
        ::= { vdslLoopSpeedTestEntry 2 }


       vdslLoopSpeedTestUSRate OBJECT-TYPE
        SYNTAX      Counter32
        MAX-ACCESS read-only
        STATUS      current
        DESCRIPTION "The result of the last loopspeed test, indicating the
                     upstream speed rate, divide by 100 to get
                     the actual value."
        ::= { vdslLoopSpeedTestEntry 3 }

       vdslLoopSpeedTestResult OBJECT-TYPE
        SYNTAX      INTEGER
            {
                    idle(1),
                    inProgress(2),
                    waitingDefaultSpeedLinkUp(3),
                    beginToTest(4),
                    completed(5),
                    fail(6)
                 }
        MAX-ACCESS read-only
        STATUS      current
        DESCRIPTION "The result of the last loopspeed test,
                    idle(1),
                    inProgress(2),
                    waitingDefaultSpeedLinkUp(3),
                    beginToTest(4),
                    completed(5),
                    fail(6)."
        ::= { vdslLoopSpeedTestEntry 4 }



--
-- vdsl4bMgt
--

vdsl4bMgt           OBJECT IDENTIFIER ::= { vdslMgt 7 }

-- Management for 4 band vdsl

--vdsl4bConfigTable

    vdsl4bConfigTable OBJECT-TYPE
        SYNTAX     SEQUENCE OF Vdsl4bConfigEntry
        MAX-ACCESS not-accessible
        STATUS     current
        DESCRIPTION "Config Paramter for each VDSL port."
        ::= { vdsl4bMgt 1 }

    vdsl4bConfigEntry OBJECT-TYPE
        SYNTAX     Vdsl4bConfigEntry
        MAX-ACCESS not-accessible
        STATUS     current
        DESCRIPTION "The entry of config table."
        INDEX       { vdsl4bConfigIndex }
        ::= { vdsl4bConfigTable 1 }

    Vdsl4bConfigEntry ::=
        SEQUENCE {
            vdsl4bConfigIndex                       InterfaceIndex,
            vdsl4bConfigActive                      INTEGER,
            vdsl4bConfigRDL                         INTEGER,
            vdsl4bConfigProfile                     INTEGER,
            vdsl4bConfigRateAdpt                    EnabledStatus,
            vdsl4bConfigDsMValue                    Integer32,
            vdsl4bConfigDsIValue                    Integer32,
            vdsl4bConfigUsMValue                    Integer32,
            vdsl4bConfigUsIValue                    Integer32,
            vdsl4bConfigPBOStatus                   EnabledStatus
        }

    vdsl4bConfigIndex OBJECT-TYPE
        SYNTAX      InterfaceIndex
        MAX-ACCESS  not-accessible
        STATUS      current
        DESCRIPTION "An index value that uniquely identifies an
                   interface to a VDSL port. The
                   interface identified by a particular value of
                   this index is the same interface as identified
                   by the same value of the ifIndex."
        ::= { vdsl4bConfigEntry 1 }

    vdsl4bConfigActive OBJECT-TYPE
        SYNTAX      INTEGER
                    {
                        active(1),
                        deactive(2)
                    }
        MAX-ACCESS  read-write
        STATUS      current
        DESCRIPTION "The active status of the VDSL port;
                     set to 1 to activate the port, set to 2 to
                     deactivate the port."
        ::= { vdsl4bConfigEntry 2 }

    vdsl4bConfigRDL OBJECT-TYPE
        SYNTAX      INTEGER
                      {
                        enable(1),
                        disable(2)
                       }
        MAX-ACCESS  read-write
        STATUS      current
        DESCRIPTION "The status of RDL;
                     set to 1 to turn on RDL, set to 2 to
                     turn off RDL."
        ::= { vdsl4bConfigEntry 3 }

    vdsl4bConfigProfile OBJECT-TYPE
        SYNTAX      INTEGER
                      {
                        a1-02oag-r1(1),
                        a2-02oag-r1(2),
                        a3-01oag-r1(3),
                        a4-01oag-r1(4),
                        s1-03oag-r1(5),
                        s2-03oag-r1(6),
                        s3-00oag-r1(7),
                        s1-16-16(8),
                        s2-16-16a(9),
                        a1-34-11(10),
                        a2-34-11a(11),
                        a3-25-3(12),
                        a4-45-5(13),
                        a5-50-7(14),
                        a6-22-3a(15),
                        a7-40-5a(16),
                        a8-46-7a(17),
                        tlan(18),
                        max-rate(19)
                     }
        MAX-ACCESS  read-write
        STATUS      current
        DESCRIPTION "The Profile ID of the port.
                     change this value to change to different
                     VDSL line rate speeds."
        ::= { vdsl4bConfigEntry 4 }

    vdsl4bConfigRateAdpt OBJECT-TYPE
        SYNTAX      EnabledStatus
        MAX-ACCESS  read-write
        STATUS      current
        DESCRIPTION "Rate adpt value of the 4 band vdsl.
                    Set to 1 to enable, set to 2 to disable."
        ::= { vdsl4bConfigEntry 5 }

    vdsl4bConfigDsMValue  OBJECT-TYPE
        SYNTAX      Integer32 (0..64)
        MAX-ACCESS  read-write
        STATUS      current
        DESCRIPTION "The downstream M interleave value."
        ::= { vdsl4bConfigEntry 6 }

    vdsl4bConfigDsIValue  OBJECT-TYPE
        SYNTAX      Integer32 (4|8)
        MAX-ACCESS  read-write
        STATUS      current
        DESCRIPTION "The downstream I interleave value."
        ::= { vdsl4bConfigEntry 7 }

    vdsl4bConfigUsMValue  OBJECT-TYPE
        SYNTAX      Integer32 (0..64)
        MAX-ACCESS  read-write
        STATUS      current
        DESCRIPTION "The upstream M interleave value."
        ::= { vdsl4bConfigEntry 8 }

    vdsl4bConfigUsIValue  OBJECT-TYPE
        SYNTAX      Integer32 (4|8)
        MAX-ACCESS  read-write
        STATUS      current
        DESCRIPTION "The upstream I interleave value."
        ::= { vdsl4bConfigEntry 9 }

    vdsl4bConfigPBOStatus OBJECT-TYPE
        SYNTAX      EnabledStatus
        MAX-ACCESS  read-write
        STATUS      current
        DESCRIPTION "To enable/disable the power back off (PBO) mechanism.
                    set to 1 to enable, set to 2 to disable."
        ::= { vdsl4bConfigEntry 10 }

--vdsl4bGenStatusTable

    vdsl4bGenStatusTable OBJECT-TYPE
        SYNTAX     SEQUENCE OF Vdsl4bGenStatusEntry
        MAX-ACCESS not-accessible
        STATUS     current
        DESCRIPTION "VDSL Link General Status."
        ::= { vdsl4bMgt 2 }

    vdsl4bGenStatusEntry  OBJECT-TYPE
        SYNTAX     Vdsl4bGenStatusEntry
        MAX-ACCESS not-accessible
        STATUS     current
        DESCRIPTION "The general status entry."
        INDEX       { vdsl4bGenStatusPortIndex }
        ::= { vdsl4bGenStatusTable 1 }

    Vdsl4bGenStatusEntry ::=
        SEQUENCE {
            vdsl4bGenStatusPortIndex              InterfaceIndex,
            vdsl4bGenStatusLink                   Counter32,
            vdsl4bGenStatusFailCnt                Counter32,
            vdsl4bGenStatusRateAdptStatus         INTEGER
        }

    vdsl4bGenStatusPortIndex OBJECT-TYPE
        SYNTAX      InterfaceIndex
        MAX-ACCESS  not-accessible
        STATUS      current
        DESCRIPTION "An index value that uniquely identifies an
                   interface to a VDSL port. The
                   interface identified by a particular value of
                   this index is the same interface as identified
                   by the same value of the ifIndex."
        ::= { vdsl4bGenStatusEntry 1 }

    vdsl4bGenStatusLink OBJECT-TYPE
        SYNTAX      Counter32
        MAX-ACCESS  read-only
        STATUS      current
        DESCRIPTION "If 1 means link up, 0 means link down."
        ::= { vdsl4bGenStatusEntry 2 }

    vdsl4bGenStatusFailCnt OBJECT-TYPE
        SYNTAX      Counter32
        MAX-ACCESS  read-only
        STATUS      current
        DESCRIPTION "Link fail count."
        ::= { vdsl4bGenStatusEntry 3 }

    vdsl4bGenStatusRateAdptStatus  OBJECT-TYPE
        SYNTAX  INTEGER
             {
               off(1),
               train(2),
               ok(3)
             }
        MAX-ACCESS  read-only
        STATUS      current
        DESCRIPTION "The rate adpt status."
        ::= { vdsl4bGenStatusEntry 4 }

--vdsl4bPMDStatusTable

    vdsl4bPMDStatusTable OBJECT-TYPE
        SYNTAX     SEQUENCE OF Vdsl4bPMDStatusEntry
        MAX-ACCESS not-accessible
        STATUS     current
        DESCRIPTION "VDSL link PMD status."
        ::= { vdsl4bMgt 3 }

    vdsl4bPMDStatusEntry  OBJECT-TYPE
        SYNTAX     Vdsl4bPMDStatusEntry
        MAX-ACCESS not-accessible
        STATUS     current
        DESCRIPTION "The entry of general status table."
        INDEX       { vdsl4bPMDStatusPortIndex }
        ::= { vdsl4bPMDStatusTable 1 }

    Vdsl4bPMDStatusEntry ::=
        SEQUENCE {
            vdsl4bPMDStatusPortIndex              InterfaceIndex,
            vdsl4bPMDStatusDs1SNR                 Integer32,
            vdsl4bPMDStatusDs2SNR                 Integer32,
            vdsl4bPMDStatusUs1SNR                 Integer32,
            vdsl4bPMDStatusUs2SNR                 Integer32,
            vdsl4bPMDStatusDSRate                Counter32,
            vdsl4bPMDStatusUSRate                Counter32,
            vdsl4bPMDStatusLocalPwr               Integer32,
            vdsl4bPMDStatusRemotePwr              Integer32
        }

    vdsl4bPMDStatusPortIndex OBJECT-TYPE
        SYNTAX      InterfaceIndex
        MAX-ACCESS  not-accessible
        STATUS      current
        DESCRIPTION "An index value that uniquely identifies an
                   interface to a VDSL port. The
                   interface identified by a particular value of
                   this index is the same interface as that identified
                   by the same value of the ifIndex."
        ::= { vdsl4bPMDStatusEntry 1 }

    vdsl4bPMDStatusDs1SNR OBJECT-TYPE
        SYNTAX      Integer32
        MAX-ACCESS  read-only
        STATUS      current
        DESCRIPTION "The downstream band 1 SNR of the link.
                     Divide by 100 to get the real
                     floating value of SNR (dB)."
        ::= { vdsl4bPMDStatusEntry 2 }

    vdsl4bPMDStatusDs2SNR OBJECT-TYPE
        SYNTAX      Integer32
        MAX-ACCESS  read-only
        STATUS      current
        DESCRIPTION "The downstream band 2 SNR of the link.
                     Divide by 100 to get the real
                     floating value of SNR (dB)."
        ::= { vdsl4bPMDStatusEntry 3 }

    vdsl4bPMDStatusUs1SNR OBJECT-TYPE
        SYNTAX      Integer32
        MAX-ACCESS  read-only
        STATUS      current
        DESCRIPTION "The upstream band 1 SNR of the link.
                     Divide by 100 to get the real
                     floating value of SNR (dB)."
        ::= { vdsl4bPMDStatusEntry 4 }

    vdsl4bPMDStatusUs2SNR OBJECT-TYPE
        SYNTAX      Integer32
        MAX-ACCESS  read-only
        STATUS      current
        DESCRIPTION "The upstream band 2 SNR of the link.
                     Divide by 100 to get the real
                     floating value of SNR (dB)."
        ::= { vdsl4bPMDStatusEntry 5 }

    vdsl4bPMDStatusDSRate OBJECT-TYPE
        SYNTAX      Counter32
        MAX-ACCESS  read-only
        STATUS      current
        DESCRIPTION "Downstream Line Speed Rate.
                     Divide by 100 to get the real
                     floating value of rate (Mbps)."
        ::= { vdsl4bPMDStatusEntry 6 }

    vdsl4bPMDStatusUSRate OBJECT-TYPE
        SYNTAX      Counter32
        MAX-ACCESS  read-only
        STATUS      current
        DESCRIPTION "Upstream Line Speed Rate.
                     Divide by 100 to get the real
                     floating value of rate (Mbps)."
        ::= { vdsl4bPMDStatusEntry 7 }

    vdsl4bPMDStatusLocalPwr OBJECT-TYPE
        SYNTAX      Integer32
        MAX-ACCESS  read-only
        STATUS      current
        DESCRIPTION "Local Transmit Power level.
                     Divide by 100 to get the real
                     floating value of power level (dBm/Hz)."
        ::= { vdsl4bPMDStatusEntry 8 }

    vdsl4bPMDStatusRemotePwr OBJECT-TYPE
        SYNTAX      Integer32
        MAX-ACCESS  read-only
        STATUS      current
        DESCRIPTION "Remote Transmit Power level.
                     Divide by 100 to get the real
                     floating value of power level (dBm/Hz)."
        ::= { vdsl4bPMDStatusEntry 9 }

--vdsl4bPMSTCStatusTable

    vdsl4bPMSTCStatusTable OBJECT-TYPE
        SYNTAX     SEQUENCE OF Vdsl4bPMSTCStatusEntry
        MAX-ACCESS not-accessible
        STATUS     current
        DESCRIPTION "VDSL Link PMS-TC Status."
        ::= { vdsl4bMgt 4 }

    vdsl4bPMSTCStatusEntry  OBJECT-TYPE
        SYNTAX     Vdsl4bPMSTCStatusEntry
        MAX-ACCESS not-accessible
        STATUS     current
        DESCRIPTION "The entry of PMS-TC status table."
        INDEX       { vdsl4bPMSTCStatusPortIndex }
        ::= { vdsl4bPMSTCStatusTable 1 }

    Vdsl4bPMSTCStatusEntry ::=
        SEQUENCE {
            vdsl4bPMSTCStatusPortIndex         InterfaceIndex,
            vdsl4bPMSTCStatusDSRSErr           Counter32,
            vdsl4bPMSTCStatusUSRSErr           Counter32
        }

    vdsl4bPMSTCStatusPortIndex OBJECT-TYPE
        SYNTAX      InterfaceIndex
        MAX-ACCESS  not-accessible
        STATUS      current
        DESCRIPTION "An index value that uniquely identifies an
                   interface to an VDSL port. The
                   interface identified by a particular value of
                   this index is the same interface as identified
                   by the same value of the ifIndex."
        ::= { vdsl4bPMSTCStatusEntry 1 }

    vdsl4bPMSTCStatusDSRSErr OBJECT-TYPE
        SYNTAX      Counter32
        MAX-ACCESS  read-only
        STATUS      current
        DESCRIPTION "Downstream Reed-Solomon Errors."
        ::= { vdsl4bPMSTCStatusEntry 2 }

    vdsl4bPMSTCStatusUSRSErr OBJECT-TYPE
        SYNTAX      Counter32
        MAX-ACCESS  read-only
        STATUS      current
        DESCRIPTION "Upstream Reed-Solomon Errors."
        ::= { vdsl4bPMSTCStatusEntry 3 }

--vdsl4bLoopBackTestTable

vdsl4bLoopBackTestTable  OBJECT-TYPE
    SYNTAX          SEQUENCE OF Vdsl4bLoopBackTestEntry
    MAX-ACCESS      not-accessible
    STATUS          current
    DESCRIPTION     "The conceptual table of vdsl4bLoopBackTestEntry."
    ::= { vdsl4bMgt 5 }

vdsl4bLoopBackTestEntry OBJECT-TYPE
    SYNTAX          Vdsl4bLoopBackTestEntry
    MAX-ACCESS      not-accessible
    STATUS          current
    DESCRIPTION     "The conceptual row for vdsl4bLoopBackTestTable."
    INDEX           { vdsl4bLoopBackTestIndex }
    ::= { vdsl4bLoopBackTestTable 1 }

Vdsl4bLoopBackTestEntry ::= SEQUENCE
    {
        vdsl4bLoopBackTestIndex              Integer32,
        vdsl4bLoopBackTestAction             INTEGER,
        vdsl4bLoopBackTestResult             INTEGER
    }

vdsl4bLoopBackTestIndex  OBJECT-TYPE
        SYNTAX      Integer32
        MAX-ACCESS  not-accessible
        STATUS      current
        DESCRIPTION "The interface index of this vdsl4bLoopBackTestTable table.
                     The interface identified by a particular value
                     of this index is the same interface as identified by the same
                     value of ifIndex in the IF-MIB."
        ::= { vdsl4bLoopBackTestEntry 1 }

vdsl4bLoopBackTestAction  OBJECT-TYPE
        SYNTAX       INTEGER
                     {
                         loopBackTest(1),
                         noLoopBackTest(2)
                     }
        MAX-ACCESS  read-write
        STATUS      current
        DESCRIPTION "Set to loopBackTest(1) to perform loopspeed test.
                     When read, returns noLoopBackTest(2)
                     when no loopspeed test is being performed."
        ::= { vdsl4bLoopBackTestEntry 2 }

vdsl4bLoopBackTestResult  OBJECT-TYPE
        SYNTAX       INTEGER
                     {
                         idle(1),
                         inProgress(2),
                         ok(3),
                         fail(4)
                     }
        MAX-ACCESS  read-only
        STATUS      current
        DESCRIPTION "The last loopback test result."
        ::= { vdsl4bLoopBackTestEntry 3 }

--
-- vdslLineMgt
--

vdslLineMgt           OBJECT IDENTIFIER ::= { vdslMgt 8 }

    --
    -- objects
    --

    vdslLineTable OBJECT-TYPE
        SYNTAX       SEQUENCE OF VdslLineEntry
        MAX-ACCESS   not-accessible
        STATUS       current
        DESCRIPTION
            "This table includes common attributes describing
            both ends of the line.  It is required for all VDSL
            physical interfaces.  VDSL physical interfaces are
            those ifEntries where ifType is equal to vdsl(97)."
        ::= { vdslLineMgt 1 }

    vdslLineEntry OBJECT-TYPE
        SYNTAX       VdslLineEntry
        MAX-ACCESS   not-accessible
        STATUS       current
        DESCRIPTION  "An entry in the vdslLineTable."
        INDEX { ifIndex }
        ::= { vdslLineTable 1 }

    VdslLineEntry ::=
        SEQUENCE
            {
            vdslLineCoding                 VdslLineCodingType,
            vdslLineType                   INTEGER,
            vdslLineConfProfile            SnmpAdminString,
            vdslLineAlarmConfProfile       SnmpAdminString
            }

    vdslLineCoding OBJECT-TYPE
        SYNTAX       VdslLineCodingType
        MAX-ACCESS   read-only
        STATUS       current
        DESCRIPTION
            "Specifies the VDSL coding type used on this line."
        REFERENCE    "T1E1.4/2000-009R3, Part 1, common spec"
        ::= { vdslLineEntry 1 }

    vdslLineType OBJECT-TYPE
        SYNTAX       INTEGER
            {
            noChannel(1),         -- no channels exist
            fastOnly(2),          -- only fast channel exists
            interleavedOnly(3),   -- only interleaved channel exists
            fastOrInterleaved(4), -- either fast or interleaved channel
                                  -- exist, but only one at a time
            fastAndInterleaved(5) -- both fast and interleaved channels
                                  -- exist
            }
        MAX-ACCESS   read-only
        STATUS       current
        DESCRIPTION
            "Defines the type of VDSL physical line entity that exists,
            by defining whether and how the line is channelized.  If
            the line is channelized,  the value will be other than
            noChannel(1).  This object defines which channel type(s)
            are supported.  Defined values are:

            noChannel(1)          -- no channels exist
            fastOnly(2)           -- only fast channel exists
            interleavedOnly(3)    -- only interleaved channel exists
            fastOrInterleaved(4)  -- either fast or interleaved channel
                                  -- exist, but only one at a time
            fastAndInterleaved(5) -- both fast and interleaved channels
                                  -- exist

            In the case that the line is channelized, the manager
            can use the ifStackTable to determine the ifIndex for
            the associated channel(s)."
        REFERENCE    "T1E1.4/2000-009R3, Part 1, common spec"
        ::= { vdslLineEntry 2 }

    vdslLineConfProfile OBJECT-TYPE
        SYNTAX       SnmpAdminString (SIZE(1..32))
        MAX-ACCESS   read-write
        STATUS       current
        DESCRIPTION
            "The value of this object identifies the row
            in the VDSL Line Configuration Profile Table,
            vdslLineConfProfileTable, which applies for this
            VDSL line, and channels if applicable."
        DEFVAL       { "DEFVAL" }
        ::= { vdslLineEntry 3 }

    vdslLineAlarmConfProfile OBJECT-TYPE
        SYNTAX       SnmpAdminString (SIZE(1..32))
        MAX-ACCESS   read-write
        STATUS       current
        DESCRIPTION
            "The value of this object identifies the row in the VDSL
            Line Alarm Configuration Profile Table,
            vdslLineAlarmConfProfileTable, which applies to this
            VDSL line, and channels if applicable."
        DEFVAL       { "DEFVAL" }
        ::= { vdslLineEntry 4 }

    vdslPhysTable OBJECT-TYPE
        SYNTAX       SEQUENCE OF VdslPhysEntry
        MAX-ACCESS   not-accessible
        STATUS       current
        DESCRIPTION
            "This table provides one row for each Vtu.  Each row
            contains the Physical Layer Parameters table for that
            Vtu.  VDSL physical interfaces are those ifEntries where
            ifType is equal to vdsl(97)."
        ::= { vdslLineMgt 2 }

    vdslPhysEntry OBJECT-TYPE
        SYNTAX       VdslPhysEntry
        MAX-ACCESS   not-accessible
        STATUS       current
        DESCRIPTION  "An entry in the vdslPhysTable."
        INDEX { ifIndex,
                vdslPhysSide }
        ::= { vdslPhysTable 1 }

    VdslPhysEntry ::=
        SEQUENCE
            {
            vdslPhysSide                   VdslLineEntity,
            vdslInvSerialNumber            SnmpAdminString,
            vdslInvVendorID                SnmpAdminString,
            vdslInvVersionNumber           SnmpAdminString,
            vdslCurrSnrMgn                 Integer32,
            vdslCurrAtn                    Gauge32,
            vdslCurrStatus                 BITS,
            vdslCurrOutputPwr              Integer32,
            vdslCurrAttainableRate         Gauge32,
            vdslCurrLineRate               Gauge32
            }

    vdslPhysSide OBJECT-TYPE
        SYNTAX       VdslLineEntity
        MAX-ACCESS   not-accessible
        STATUS       current
        DESCRIPTION
            "Identifies whether the transceiver is the Vtuc or Vtur."
        ::= { vdslPhysEntry 1 }

    vdslInvSerialNumber OBJECT-TYPE
        SYNTAX       SnmpAdminString(SIZE (0..32))
        MAX-ACCESS   read-only
        STATUS       current
        DESCRIPTION
            "The vendor specific string that identifies the
            vendor equipment."
        REFERENCE    "T1E1.4/2000-009R3, Part 1, common spec"
        ::= { vdslPhysEntry 2 }

    vdslInvVendorID OBJECT-TYPE
        SYNTAX       SnmpAdminString (SIZE (0..16))
        MAX-ACCESS   read-only
        STATUS       current
        DESCRIPTION
            "The vendor ID code is a copy of the binary vendor
            identification field expressed as readable characters
            in hexadecimal notation."
        REFERENCE    "T1E1.4/2000-009R3, Part 1, common spec"
        ::= { vdslPhysEntry 3 }

    vdslInvVersionNumber OBJECT-TYPE
        SYNTAX       SnmpAdminString (SIZE (0..16))
        MAX-ACCESS   read-only
        STATUS       current
        DESCRIPTION
            "The vendor specific version number sent by this Vtu
            as part of the initialization messages.  It is a copy
            of the binary version number field expressed as
            readable characters in hexadecimal notation."
        REFERENCE    "T1E1.4/2000-009R3, Part 1, common spec"
        ::= { vdslPhysEntry 4 }

    vdslCurrSnrMgn OBJECT-TYPE
        SYNTAX       Integer32 (-127..127)
        UNITS        "0.25dBm"
        MAX-ACCESS   read-only
        STATUS       current
        DESCRIPTION
            "Noise Margin as seen by this Vtu with respect to its
            received signal in 0.25dB.  The effective range is
            -31.75 to +31.75 dB."
        REFERENCE    "T1E1.4/2000-009R3, Part 1, common spec"
         ::= { vdslPhysEntry 5 }

    vdslCurrAtn OBJECT-TYPE
        SYNTAX       Gauge32 (0..255)
        UNITS        "0.25dBm"
        MAX-ACCESS   read-only
        STATUS       current
        DESCRIPTION
            "Measured difference in the total power transmitted by
            the peer Vtu and the total power received by this Vtu.
            The effective range is 0 to +63.75 dB."
        REFERENCE    "T1E1.4/2000-009R3, Part 1, common spec"
         ::= { vdslPhysEntry 6 }

    vdslCurrStatus OBJECT-TYPE
        SYNTAX       BITS
            {
            noDefect(0),
            lossOfFraming(1),
            lossOfSignal(2),
            lossOfPower(3),
            lossOfSignalQuality(4),
            lossOfLink(5),
            dataInitFailure(6),
            configInitFailure(7),
            protocolInitFailure(8),
            noPeerVtuPresent(9)
            }
        MAX-ACCESS  read-only
        STATUS      current
        DESCRIPTION
            "Indicates current state of the Vtu line.  This is a
            bit-map of possible conditions.  The various bit
            positions are:

            0   noDefect             There are no defects on the line.

            1   lossOfFraming        Vtu failure due to not receiving
                                     a valid frame.

            2   lossOfSignal         Vtu failure due to not receiving
                                     signal.

            3   lossOfPower          Vtu failure due to loss of power.

            4   lossOfSignalQuality  Loss of Signal Quality is declared
                                     when the Noise Margin falls below
                                     the Minimum Noise Margin, or the
                                     bit-error-rate exceeds 10^-7.
            5   lossOfLink           Vtu failure due to inability to
                                     link with peer Vtu.  Set whenever
                                     the transceiver is in the 'Warm
                                     Start' state.

            6   dataInitFailure      Vtu failure during initialization
                                     due to bit errors corrupting
                                     startup exchange data.

            7   configInitFailure    Vtu failure during initialization
                                     due to peer Vtu not able to
                                     support requested configuration.

            8   protocolInitFailure  Vtu failure during initialization
                                     due to incompatible protocol used
                                     by the peer Vtu.

            9   noPeerVtuPresent     Vtu failure during initialization
                                     due to no activation sequence
                                     detected from peer Vtu.

            This is intended to supplement ifOperStatus."
        REFERENCE    "T1E1.4/2000-009R3, Part 1, common spec"
         ::= { vdslPhysEntry 7 }

    vdslCurrOutputPwr OBJECT-TYPE
        SYNTAX       Integer32 (0..160)
        UNITS        "0.1dBm"
        MAX-ACCESS   read-only
        STATUS       current
        DESCRIPTION
            "Measured total output power transmitted by this VTU.
            This is the measurement that was reported during
            the last activation sequence."
        REFERENCE    "T1E1.4/2000-009R3, Part 1, common spec"
        ::= { vdslPhysEntry 8 }

    vdslCurrAttainableRate OBJECT-TYPE
        SYNTAX       Gauge32
        UNITS        "kbps"
        MAX-ACCESS   read-only
        STATUS       current
        DESCRIPTION
            "Indicates the maximum currently attainable data rate
            in steps of 1000 bits/second by the Vtu.  This value
            will be equal to or greater than vdslCurrLineRate.
            Note that for SCM, the minimum and maximum data rates
            are equal.  Note: 1 kbps = 1000 bps."
        REFERENCE    "T1E1.4/2000-009R3, Part 1, common spec"
        ::= { vdslPhysEntry 9 }

    vdslCurrLineRate OBJECT-TYPE
        SYNTAX       Gauge32
        UNITS        "kbps"
        MAX-ACCESS   read-only
        STATUS       current
        DESCRIPTION
            "Indicates the current data rate in steps of 1000
            bits/second by the Vtu.  This value will be less than
            or equal to vdslCurrAttainableRate.  Note: 1 kbps =
            1000 bps."
        REFERENCE    "T1E1.4/2000-009R3, Part 1, common spec"
        ::= { vdslPhysEntry 10 }

    vdslChanTable OBJECT-TYPE
        SYNTAX       SEQUENCE OF VdslChanEntry
        MAX-ACCESS   not-accessible
        STATUS       current
        DESCRIPTION
            "This table provides one row for each Vtu channel.
            VDSL channel interfaces are those ifEntries where
            ifType is equal to interleave(124) or fast(125)."
        ::= { vdslLineMgt 3 }

    vdslChanEntry OBJECT-TYPE
        SYNTAX       VdslChanEntry
        MAX-ACCESS   not-accessible
        STATUS       current
        DESCRIPTION
            "An entry in the vdslChanTable."
        INDEX { ifIndex,
                vdslPhysSide }
        ::= { vdslChanTable 1 }

    VdslChanEntry ::=
        SEQUENCE
            {
            vdslChanInterleaveDelay        Gauge32,
            vdslChanCrcBlockLength         Gauge32,
            vdslChanCurrTxRate             Gauge32,
            vdslChanCurrTxSlowBurstProtect Gauge32,
            vdslChanCurrTxFastFec          Gauge32
            }

    vdslChanInterleaveDelay OBJECT-TYPE
        SYNTAX       Gauge32
        UNITS        "milliseconds"
        MAX-ACCESS   read-only
        STATUS       current
        DESCRIPTION
            "Interleave Delay for this channel.

            Interleave delay applies only to the interleave
            (slow) channel and defines the mapping (relative
            spacing) between subsequent input bytes at the
            interleaver input and their placement in the bit
            stream at the interleaver output.  Larger numbers
            provide greater separation between consecutive
            input bytes in the output bit stream allowing for
            improved impulse noise immunity at the expense of
            payload latency.

            In the case where the ifType is fast(125), return
            a value of zero."
        REFERENCE    "T1E1.4/2000-009R3, Part 1, common spec"
        ::= { vdslChanEntry 1 }

    vdslChanCrcBlockLength OBJECT-TYPE
        SYNTAX       Gauge32
        UNITS        "bytes"
        MAX-ACCESS   read-only
        STATUS       current
        DESCRIPTION
            "Indicates the length of the channel data-block
            on which the CRC operates."
        REFERENCE    "T1E1.4/2000-009R3, Part 1, common spec"
        ::= { vdslChanEntry 2 }

    vdslChanCurrTxRate OBJECT-TYPE
        SYNTAX       Gauge32
        UNITS        "kbps"
        MAX-ACCESS   read-only
        STATUS       current
        DESCRIPTION
            "Actual transmit data rate on this channel.  Note: 1
            kbps = 1000 bps."
        ::= { vdslChanEntry 3 }

    vdslChanCurrTxSlowBurstProtect OBJECT-TYPE
        SYNTAX       Gauge32 (0..1275)
        UNITS        "microseconds"
        MAX-ACCESS   read-only
        STATUS       current
        DESCRIPTION
            "Actual level of impulse noise (burst) protection
            for an interleaved (slow) channel.  This parameter is
            not applicable to fast channels.  For fast channels,
            a value of zero shall be returned."
        REFERENCE    "ITU-T G.997.1, section 7.3.2.3"
        ::= { vdslChanEntry 4 }

    vdslChanCurrTxFastFec OBJECT-TYPE
        SYNTAX       Gauge32 (0..50)
        UNITS        "%"
        MAX-ACCESS   read-only
        STATUS       current
        DESCRIPTION
            "Actual Forward Error Correction (FEC) redundancy
            related overhead for a fast channel.  This parameter
            is not applicable to an interleaved (slow) channel.
            For interleaved channels, a value of zero shall be
            returned."
        ::= { vdslChanEntry 5 }

    vdslPerfDataTable       OBJECT-TYPE
        SYNTAX       SEQUENCE OF VdslPerfDataEntry
        MAX-ACCESS   not-accessible
        STATUS       current
        DESCRIPTION
            "This table provides one row for each VDSL physical
            interface.  VDSL physical interfaces are those ifEntries
            where ifType is equal to vdsl(97)."
        ::= { vdslLineMgt 4 }

    vdslPerfDataEntry       OBJECT-TYPE
        SYNTAX        VdslPerfDataEntry
        MAX-ACCESS    not-accessible
        STATUS        current
        DESCRIPTION
            "An entry in the vdslPerfDataTable."
        INDEX { ifIndex,
                vdslPhysSide }
        ::= { vdslPerfDataTable 1 }

    VdslPerfDataEntry ::=
        SEQUENCE
            {
            vdslPerfValidIntervals         HCPerfValidIntervals,
            vdslPerfInvalidIntervals       HCPerfInvalidIntervals,
            vdslPerfLofs                   Unsigned32,
            vdslPerfLoss                   Unsigned32,
            vdslPerfLprs                   Unsigned32,
            vdslPerfLols                   Unsigned32,
            vdslPerfESs                    Unsigned32,
            vdslPerfSESs                   Unsigned32,
            vdslPerfUASs                   Unsigned32,
            vdslPerfInits                  Unsigned32,
            vdslPerfCurr15MinTimeElapsed   HCPerfTimeElapsed,
            vdslPerfCurr15MinLofs          HCPerfCurrentCount,
            vdslPerfCurr15MinLoss          HCPerfCurrentCount,
            vdslPerfCurr15MinLprs          HCPerfCurrentCount,
            vdslPerfCurr15MinLols          HCPerfCurrentCount,
            vdslPerfCurr15MinESs           HCPerfCurrentCount,
            vdslPerfCurr15MinSESs          HCPerfCurrentCount,
            vdslPerfCurr15MinUASs          HCPerfCurrentCount,
            vdslPerfCurr15MinInits         HCPerfCurrentCount,
            vdslPerf1DayValidIntervals     HCPerfValidIntervals,
            vdslPerf1DayInvalidIntervals   HCPerfInvalidIntervals,
            vdslPerfCurr1DayTimeElapsed    HCPerfTimeElapsed,
            vdslPerfCurr1DayLofs           Unsigned32,
            vdslPerfCurr1DayLoss           Unsigned32,
            vdslPerfCurr1DayLprs           Unsigned32,
            vdslPerfCurr1DayLols           Unsigned32,
            vdslPerfCurr1DayESs            Unsigned32,
            vdslPerfCurr1DaySESs           Unsigned32,
            vdslPerfCurr1DayUASs           Unsigned32,
            vdslPerfCurr1DayInits          Unsigned32
            }

    vdslPerfValidIntervals OBJECT-TYPE
        SYNTAX       HCPerfValidIntervals
        UNITS        "intervals"
        MAX-ACCESS   read-only
        STATUS       current
        DESCRIPTION
            "Valid Intervals per definition found in
            HC-PerfHist-TC-MIB."
        ::= { vdslPerfDataEntry 1 }

    vdslPerfInvalidIntervals OBJECT-TYPE
        SYNTAX       HCPerfInvalidIntervals
        UNITS        "intervals"
        MAX-ACCESS   read-only
        STATUS       current
        DESCRIPTION
            "Invalid Intervals per definition found in
            HC-PerfHist-TC-MIB."
        ::= { vdslPerfDataEntry 2 }

    vdslPerfLofs OBJECT-TYPE
        SYNTAX       Unsigned32
        UNITS        "seconds"
        MAX-ACCESS   read-only
        STATUS       current
        DESCRIPTION
            "Count of seconds since the unit was last reset that there
            was Loss of Framing."
        REFERENCE    "T1E1.4/2000-009R3, Part 1, common spec"
        ::= { vdslPerfDataEntry 3 }

    vdslPerfLoss OBJECT-TYPE
        SYNTAX       Unsigned32
        UNITS        "seconds"
        MAX-ACCESS   read-only
        STATUS       current
        DESCRIPTION
            "Count of seconds since the unit was last reset that there
            was Loss of Signal."
        REFERENCE    "T1E1.4/2000-009R3, Part 1, common spec"
        ::= { vdslPerfDataEntry 4 }

    vdslPerfLprs OBJECT-TYPE
        SYNTAX       Unsigned32
        UNITS        "seconds"
        MAX-ACCESS   read-only
        STATUS       current
        DESCRIPTION
            "Count of seconds since the unit was last reset that there
            was Loss of Power."
        REFERENCE    "T1E1.4/2000-009R3, Part 1, common spec"
        ::= { vdslPerfDataEntry 5 }

    vdslPerfLols OBJECT-TYPE
        SYNTAX       Unsigned32
        UNITS        "seconds"
        MAX-ACCESS   read-only
        STATUS       current
        DESCRIPTION
            "Count of seconds since the unit was last reset that there
            was Loss of Link."
        ::= { vdslPerfDataEntry 6 }

    vdslPerfESs OBJECT-TYPE
        SYNTAX       Unsigned32
        UNITS        "seconds"
        MAX-ACCESS   read-only
        STATUS       current
        DESCRIPTION
            "Count of Errored Seconds since the unit was last reset.
            An Errored Second is a one-second interval containing one
            or more CRC anomalies, or one or more LOS or LOF defects."
        REFERENCE    "T1E1.4/2000-009R3, Part 1, common spec"
        ::= { vdslPerfDataEntry 7 }

    vdslPerfSESs OBJECT-TYPE
        SYNTAX       Unsigned32
        UNITS        "seconds"
        MAX-ACCESS   read-only
        STATUS       current
        DESCRIPTION
            "Count of Severely Errored Seconds since the unit was last
            reset."
        ::= { vdslPerfDataEntry 8 }

    vdslPerfUASs OBJECT-TYPE
        SYNTAX       Unsigned32
        UNITS        "seconds"
        MAX-ACCESS   read-only
        STATUS       current
        DESCRIPTION
            "Count of Unavailable Seconds since the unit was last
            reset."
        ::= { vdslPerfDataEntry 9 }

    vdslPerfInits OBJECT-TYPE
        SYNTAX       Unsigned32
        UNITS        "occurences"
        MAX-ACCESS   read-only
        STATUS       current
        DESCRIPTION
            "Count of the line initialization attempts since the unit
            was last reset.  This count includes both successful and
            failed attempts."
        REFERENCE    "T1E1.4/2000-009R3, Part 1, common spec"
        ::= { vdslPerfDataEntry 10 }

    vdslPerfCurr15MinTimeElapsed OBJECT-TYPE
        SYNTAX       HCPerfTimeElapsed
        UNITS        "seconds"
        MAX-ACCESS   read-only
        STATUS       current
        DESCRIPTION
            "Total elapsed seconds in this interval."
        ::= { vdslPerfDataEntry 11 }

    vdslPerfCurr15MinLofs OBJECT-TYPE
        SYNTAX       HCPerfCurrentCount
        UNITS        "seconds"
        MAX-ACCESS   read-only
        STATUS       current
        DESCRIPTION
            "Count of seconds during this interval that there
            was Loss of Framing."
        REFERENCE    "T1E1.4/2000-009R3, Part 1, common spec"
        ::= { vdslPerfDataEntry 12 }

    vdslPerfCurr15MinLoss OBJECT-TYPE
        SYNTAX       HCPerfCurrentCount
        UNITS        "seconds"
        MAX-ACCESS   read-only
        STATUS       current
        DESCRIPTION
            "Count of seconds during this interval that there
            was Loss of Signal."
        REFERENCE    "T1E1.4/2000-009R3, Part 1, common spec"
        ::= { vdslPerfDataEntry 13 }

    vdslPerfCurr15MinLprs OBJECT-TYPE
        SYNTAX       HCPerfCurrentCount
        UNITS        "seconds"
        MAX-ACCESS   read-only
        STATUS       current
        DESCRIPTION
            "Count of seconds during this interval that there
            was Loss of Power."
        REFERENCE    "T1E1.4/2000-009R3, Part 1, common spec"
        ::= { vdslPerfDataEntry 14 }

    vdslPerfCurr15MinLols OBJECT-TYPE
        SYNTAX       HCPerfCurrentCount
        UNITS        "seconds"
        MAX-ACCESS   read-only
        STATUS       current
        DESCRIPTION
            "Count of seconds during this interval that there
            was Loss of Link."
        ::= { vdslPerfDataEntry 15 }

    vdslPerfCurr15MinESs OBJECT-TYPE
        SYNTAX       HCPerfCurrentCount
        UNITS        "seconds"
        MAX-ACCESS   read-only
        STATUS       current
        DESCRIPTION
            "Count of Errored Seconds during this interval.  An Errored
            Second is a one-second interval containing one or more CRC
            anomalies, or one or more LOS or LOF defects."
        REFERENCE    "T1E1.4/2000-009R3, Part 1, common spec"
        ::= { vdslPerfDataEntry 16 }

    vdslPerfCurr15MinSESs OBJECT-TYPE
        SYNTAX       HCPerfCurrentCount
        UNITS        "seconds"
        MAX-ACCESS   read-only
        STATUS       current
        DESCRIPTION
            "Count of Severely Errored Seconds during this interval."
        ::= { vdslPerfDataEntry 17 }

    vdslPerfCurr15MinUASs OBJECT-TYPE
        SYNTAX       HCPerfCurrentCount
        UNITS        "seconds"
        MAX-ACCESS   read-only
        STATUS       current
        DESCRIPTION
            "Count of Unavailable Seconds during this interval."
        ::= { vdslPerfDataEntry 18 }

    vdslPerfCurr15MinInits OBJECT-TYPE
        SYNTAX       HCPerfCurrentCount
        UNITS        "occurences"
        MAX-ACCESS   read-only
        STATUS       current
        DESCRIPTION
            "Count of the line initialization attempts during this
            interval.  This count includes both successful and
            failed attempts."
        REFERENCE    "T1E1.4/2000-009R3, Part 1, common spec"
        ::= { vdslPerfDataEntry 19 }

    vdslPerf1DayValidIntervals OBJECT-TYPE
        SYNTAX       HCPerfValidIntervals
        UNITS        "intervals"
        MAX-ACCESS   read-only
        STATUS       current
        DESCRIPTION
            "Valid Intervals per definition found in
            HC-PerfHist-TC-MIB."
        ::= { vdslPerfDataEntry 20 }

    vdslPerf1DayInvalidIntervals OBJECT-TYPE
        SYNTAX       HCPerfInvalidIntervals
        UNITS        "intervals"
        MAX-ACCESS   read-only
        STATUS       current
        DESCRIPTION
            "Invalid Intervals per definition found in
            HC-PerfHist-TC-MIB."
        ::= { vdslPerfDataEntry 21 }

    vdslPerfCurr1DayTimeElapsed OBJECT-TYPE
        SYNTAX       HCPerfTimeElapsed
        UNITS        "seconds"
        MAX-ACCESS   read-only
        STATUS       current
        DESCRIPTION
             "Number of seconds that have elapsed since the beginning
             of the current 1-day interval."
        ::= { vdslPerfDataEntry 22 }

    vdslPerfCurr1DayLofs OBJECT-TYPE
        SYNTAX       Unsigned32
        UNITS        "seconds"
        MAX-ACCESS   read-only
        STATUS       current
        DESCRIPTION
            "Count of Loss of Framing (LOF) Seconds since the
            beginning of the current 1-day interval."
        ::= { vdslPerfDataEntry 23 }

    vdslPerfCurr1DayLoss OBJECT-TYPE
        SYNTAX       Unsigned32
        UNITS        "seconds"
        MAX-ACCESS   read-only
        STATUS       current
        DESCRIPTION
            "Count of Loss of Signal (LOS) Seconds since the beginning
            of the current 1-day interval."
        ::= { vdslPerfDataEntry 24 }

    vdslPerfCurr1DayLprs OBJECT-TYPE
        SYNTAX       Unsigned32
        UNITS        "seconds"
        MAX-ACCESS   read-only
        STATUS       current
        DESCRIPTION
            "Count of Loss of Power (LPR) Seconds since the beginning
            of the current 1-day interval."
        ::= { vdslPerfDataEntry 25 }

    vdslPerfCurr1DayLols OBJECT-TYPE
        SYNTAX       Unsigned32
        UNITS        "seconds"
        MAX-ACCESS   read-only
        STATUS       current
        DESCRIPTION
            "Count of Loss of Link (LOL) Seconds since the beginning
            of the current 1-day interval."
        ::= { vdslPerfDataEntry 26 }

    vdslPerfCurr1DayESs OBJECT-TYPE
        SYNTAX       Unsigned32
        UNITS        "seconds"
        MAX-ACCESS   read-only
        STATUS       current
        DESCRIPTION
            "Count of Errored Seconds (ES) since the beginning
            of the current 1-day interval."
        ::= { vdslPerfDataEntry 27 }

    vdslPerfCurr1DaySESs OBJECT-TYPE
        SYNTAX       Unsigned32
        UNITS        "seconds"
        MAX-ACCESS   read-only
        STATUS       current
        DESCRIPTION
            "Count of Severely Errored Seconds (SES) since the
            beginning of the current 1-day interval."
        ::= { vdslPerfDataEntry 28 }

    vdslPerfCurr1DayUASs OBJECT-TYPE
        SYNTAX       Unsigned32
        UNITS        "seconds"
        MAX-ACCESS   read-only
        STATUS       current
        DESCRIPTION
            "Count of Unavailable Seconds (UAS) since the beginning
            of the current 1-day interval."
        ::= { vdslPerfDataEntry 29 }

    vdslPerfCurr1DayInits OBJECT-TYPE
        SYNTAX       Unsigned32
        UNITS        "seconds"
        MAX-ACCESS   read-only
        STATUS       current
        DESCRIPTION
            "Count of the line initialization attempts since the
            beginning of the current 1-day interval.  This count
            includes both successful and failed attempts."
        ::= { vdslPerfDataEntry 30 }

    vdslPerfIntervalTable       OBJECT-TYPE
        SYNTAX       SEQUENCE OF VdslPerfIntervalEntry
        MAX-ACCESS   not-accessible
        STATUS       current
        DESCRIPTION
            "This table provides one row for each Vtu performance
            data collection interval.  VDSL physical interfaces are
            those ifEntries where ifType is equal to vdsl(97)."
        ::= { vdslLineMgt 5 }

    vdslPerfIntervalEntry       OBJECT-TYPE
        SYNTAX        VdslPerfIntervalEntry
        MAX-ACCESS    not-accessible
        STATUS        current
        DESCRIPTION
            "An entry in the vdslPerfIntervalTable."
        INDEX { ifIndex,
                vdslPhysSide,
                vdslIntervalNumber }
        ::= { vdslPerfIntervalTable 1 }

    VdslPerfIntervalEntry ::=
        SEQUENCE
            {
            vdslIntervalNumber             Unsigned32,
            vdslIntervalLofs               HCPerfIntervalCount,
            vdslIntervalLoss               HCPerfIntervalCount,
            vdslIntervalLprs               HCPerfIntervalCount,
            vdslIntervalLols               HCPerfIntervalCount,
            vdslIntervalESs                HCPerfIntervalCount,
            vdslIntervalSESs               HCPerfIntervalCount,
            vdslIntervalUASs               HCPerfIntervalCount,
            vdslIntervalInits              HCPerfIntervalCount
            }

    vdslIntervalNumber OBJECT-TYPE
        SYNTAX       Unsigned32 (1..96)
        MAX-ACCESS   not-accessible
        STATUS       current
        DESCRIPTION
            "Performance Data Interval number 1 is the most recent
            previous interval; interval 96 is 24 hours ago.
            Intervals 2 to 96 are optional."
        ::= { vdslPerfIntervalEntry 1 }

    vdslIntervalLofs OBJECT-TYPE
        SYNTAX       HCPerfIntervalCount
        UNITS        "seconds"
        MAX-ACCESS   read-only
        STATUS       current
        DESCRIPTION
            "Count of seconds in the interval when there was Loss
            of Framing."
        REFERENCE    "T1E1.4/2000-009R3, Part 1, common spec"
        ::= { vdslPerfIntervalEntry 2 }

    vdslIntervalLoss OBJECT-TYPE
        SYNTAX       HCPerfIntervalCount
        UNITS        "seconds"
        MAX-ACCESS   read-only
        STATUS       current
        DESCRIPTION
            "Count of seconds in the interval when there was Loss
            of Signal."
        REFERENCE    "T1E1.4/2000-009R3, Part 1, common spec"
        ::= { vdslPerfIntervalEntry 3 }

    vdslIntervalLprs OBJECT-TYPE
        SYNTAX       HCPerfIntervalCount
        UNITS        "seconds"
        MAX-ACCESS   read-only
        STATUS       current
        DESCRIPTION
            "Count of seconds in the interval when there was Loss
            of Power."
        REFERENCE    "T1E1.4/2000-009R3, Part 1, common spec"
        ::= { vdslPerfIntervalEntry 4 }

    vdslIntervalLols OBJECT-TYPE
        SYNTAX       HCPerfIntervalCount
        UNITS        "seconds"
        MAX-ACCESS   read-only
        STATUS       current
        DESCRIPTION
            "Count of seconds in the interval when there was Loss
            of Link."
        ::= { vdslPerfIntervalEntry 5 }

    vdslIntervalESs OBJECT-TYPE
        SYNTAX       HCPerfIntervalCount
        UNITS        "seconds"
        MAX-ACCESS   read-only
        STATUS       current
        DESCRIPTION
            "Count of Errored Seconds (ES) in the interval.  An Errored
            Second is a one-second interval containing one or more CRC
            anomalies, one or more LOS or LOF defects."
        REFERENCE    "T1E1.4/2000-009R3, Part 1, common spec"
        ::= { vdslPerfIntervalEntry 6 }

    vdslIntervalSESs OBJECT-TYPE
        SYNTAX       HCPerfIntervalCount
        UNITS        "seconds"
        MAX-ACCESS   read-only
        STATUS       current
        DESCRIPTION
            "Count of Severely Errored Seconds in the interval."
        ::= { vdslPerfIntervalEntry 7 }

    vdslIntervalUASs OBJECT-TYPE
        SYNTAX       HCPerfIntervalCount
        UNITS        "seconds"
        MAX-ACCESS   read-only
        STATUS       current
        DESCRIPTION
            "Count of Unavailable Seconds in the interval."
        ::= { vdslPerfIntervalEntry 8 }

    vdslIntervalInits OBJECT-TYPE
        SYNTAX       HCPerfIntervalCount
        MAX-ACCESS   read-only
        STATUS       current
        DESCRIPTION
            "Count of the line initialization attempts during this
            interval.  This count includes both successful and
            failed attempts."
        REFERENCE    "T1E1.4/2000-009R3, Part 1, common spec"
        ::= { vdslPerfIntervalEntry 9 }

    vdsl1DayIntervalTable OBJECT-TYPE
        SYNTAX       SEQUENCE OF Vdsl1DayIntervalEntry
        MAX-ACCESS   not-accessible
        STATUS       current
        DESCRIPTION
            "This table provides one row for each VDSL performance
            data collection interval.  This table contains live data
            from equipment.  As such, it is NOT persistent."
        ::= { vdslLineMgt 6 }

    vdsl1DayIntervalEntry OBJECT-TYPE
        SYNTAX       Vdsl1DayIntervalEntry
        MAX-ACCESS   not-accessible
        STATUS       current
        DESCRIPTION
            "An entry in the vdsl1DayIntervalTable."
        INDEX { ifIndex,
                vdslPhysSide,
                vdsl1DayIntervalNumber }
        ::= { vdsl1DayIntervalTable 1 }

    Vdsl1DayIntervalEntry ::=
        SEQUENCE
        {
        vdsl1DayIntervalNumber             Unsigned32,
        vdsl1DayIntervalMoniSecs           HCPerfTimeElapsed,
        vdsl1DayIntervalLofs               Unsigned32,
        vdsl1DayIntervalLoss               Unsigned32,
        vdsl1DayIntervalLprs               Unsigned32,
        vdsl1DayIntervalLols               Unsigned32,
        vdsl1DayIntervalESs                Unsigned32,
        vdsl1DayIntervalSESs               Unsigned32,
        vdsl1DayIntervalUASs               Unsigned32,
        vdsl1DayIntervalInits              Unsigned32
        }

    vdsl1DayIntervalNumber OBJECT-TYPE
        SYNTAX       Unsigned32 (1..30)
        MAX-ACCESS   not-accessible
        STATUS       current
        DESCRIPTION
            "History Data Interval number.  Interval 1 is the most
            recent previous day; interval 30 is 30 days ago.  Intervals
            2 to 30 are optional."
        ::= { vdsl1DayIntervalEntry 1 }

    vdsl1DayIntervalMoniSecs OBJECT-TYPE
        SYNTAX       HCPerfTimeElapsed
        UNITS        "seconds"
        MAX-ACCESS   read-only
        STATUS       current
        DESCRIPTION
            "The amount of time in the 1-day interval over which the
            performance monitoring information is actually counted.
            This value will be the same as the interval duration except
            in a situation where performance monitoring data could not
            be collected for any reason."
        ::= { vdsl1DayIntervalEntry 2 }

    vdsl1DayIntervalLofs OBJECT-TYPE
        SYNTAX       Unsigned32
        UNITS        "seconds"
        MAX-ACCESS   read-only
        STATUS       current
        DESCRIPTION
             "Count of Loss of Frame (LOF) Seconds during the 1-day
             interval as measured by vdsl1DayIntervalMoniSecs."
        REFERENCE    "T1E1.4/2000-009R3, Part 1, common spec"
        ::= { vdsl1DayIntervalEntry 3 }

    vdsl1DayIntervalLoss OBJECT-TYPE
        SYNTAX       Unsigned32
        UNITS        "seconds"
        MAX-ACCESS   read-only
        STATUS       current
        DESCRIPTION
             "Count of Loss of Signal (LOS) Seconds during the 1-day
             interval as measured by vdsl1DayIntervalMoniSecs."
        REFERENCE    "T1E1.4/2000-009R3, Part 1, common spec"
        ::= { vdsl1DayIntervalEntry 4 }

    vdsl1DayIntervalLprs OBJECT-TYPE
        SYNTAX       Unsigned32
        UNITS        "seconds"
        MAX-ACCESS   read-only
        STATUS       current
        DESCRIPTION
             "Count of Loss of Power (LPR) Seconds during the 1-day
             interval as measured by vdsl1DayIntervalMoniSecs."
        REFERENCE    "T1E1.4/2000-009R3, Part 1, common spec"
        ::= { vdsl1DayIntervalEntry 5 }

    vdsl1DayIntervalLols OBJECT-TYPE
        SYNTAX       Unsigned32
        UNITS        "seconds"
        MAX-ACCESS   read-only
        STATUS       current
        DESCRIPTION
             "Count of Loss of Link (LOL) Seconds during the 1-day
             interval as measured by vdsl1DayIntervalMoniSecs."
        ::= { vdsl1DayIntervalEntry 6 }

    vdsl1DayIntervalESs OBJECT-TYPE
        SYNTAX       Unsigned32
        UNITS        "seconds"
        MAX-ACCESS   read-only
        STATUS       current
        DESCRIPTION
             "Count of Errored Seconds (ES) during the 1-day
             interval as measured by vdsl1DayIntervalMoniSecs."
        REFERENCE    "T1E1.4/2000-009R3, Part 1, common spec"
        ::= { vdsl1DayIntervalEntry 7 }

    vdsl1DayIntervalSESs OBJECT-TYPE
        SYNTAX       Unsigned32
        UNITS        "seconds"
        MAX-ACCESS   read-only
        STATUS       current
        DESCRIPTION
             "Count of Severely Errored Seconds (SES) during the 1-day
             interval as measured by vdsl1DayIntervalMoniSecs."
        ::= { vdsl1DayIntervalEntry 8 }

    vdsl1DayIntervalUASs OBJECT-TYPE
        SYNTAX       Unsigned32
        UNITS        "seconds"
        MAX-ACCESS   read-only
        STATUS       current
        DESCRIPTION
             "Count of Unavailable Seconds (UAS) during the 1-day
             interval as measured by vdsl1DayIntervalMoniSecs."
        ::= { vdsl1DayIntervalEntry 9 }

    vdsl1DayIntervalInits OBJECT-TYPE
        SYNTAX       Unsigned32
        UNITS        "seconds"
        MAX-ACCESS   read-only
        STATUS       current
        DESCRIPTION
            "Count of the line initialization attempts during the
            1-day interval as measured by vdsl1DayIntervalMoniSecs.
            This count includes both successful and failed attempts."
        REFERENCE    "T1E1.4/2000-009R3, Part 1, common spec"
        ::= { vdsl1DayIntervalEntry 10 }

    vdslChanPerfDataTable       OBJECT-TYPE
        SYNTAX       SEQUENCE OF VdslChanPerfDataEntry
        MAX-ACCESS   not-accessible
        STATUS       current
        DESCRIPTION
            "This table provides one row for each Vtu channel.
            VDSL channel interfaces are those ifEntries where
            ifType is equal to interleave(124) or fast(125)."
        ::= { vdslLineMgt 7 }

    vdslChanPerfDataEntry OBJECT-TYPE
        SYNTAX        VdslChanPerfDataEntry
        MAX-ACCESS    not-accessible
        STATUS        current
        DESCRIPTION
            "An entry in the vdslChanPerfDataTable."
        INDEX { ifIndex,
                vdslPhysSide }
        ::= { vdslChanPerfDataTable 1 }

    VdslChanPerfDataEntry ::=
        SEQUENCE
            {
            vdslChanValidIntervals         HCPerfValidIntervals,
            vdslChanInvalidIntervals       HCPerfInvalidIntervals,
            vdslChanFixedOctets            ZeroBasedCounter64,
            vdslChanBadBlks                ZeroBasedCounter64,
            vdslChanCurr15MinTimeElapsed   HCPerfTimeElapsed,
            vdslChanCurr15MinFixedOctets   HCPerfCurrentCount,
            vdslChanCurr15MinBadBlks       HCPerfCurrentCount,
            vdslChan1DayValidIntervals     HCPerfValidIntervals,
            vdslChan1DayInvalidIntervals   HCPerfInvalidIntervals,
            vdslChanCurr1DayTimeElapsed    HCPerfTimeElapsed,
            vdslChanCurr1DayFixedOctets    HCPerfCurrentCount,
            vdslChanCurr1DayBadBlks        HCPerfCurrentCount
            }

    vdslChanValidIntervals OBJECT-TYPE
        SYNTAX        HCPerfValidIntervals
        UNITS        "intervals"
        MAX-ACCESS    read-only
        STATUS        current
        DESCRIPTION
            "Valid Intervals per definition found in
            HC-PerfHist-TC-MIB."
        ::= { vdslChanPerfDataEntry 1 }

    vdslChanInvalidIntervals OBJECT-TYPE
        SYNTAX        HCPerfInvalidIntervals
        UNITS        "intervals"
        MAX-ACCESS    read-only
        STATUS        current
        DESCRIPTION
            "Invalid Intervals per definition found in
            HC-PerfHist-TC-MIB."
        ::= { vdslChanPerfDataEntry 2 }

    vdslChanFixedOctets OBJECT-TYPE
        SYNTAX        ZeroBasedCounter64
        UNITS         "octets"
        MAX-ACCESS    read-only
        STATUS        current
        DESCRIPTION
            "Count of corrected octets since the unit was last reset."
        REFERENCE    "T1E1.4/2000-009R3, Part 1, common spec"
        ::= { vdslChanPerfDataEntry 3 }

    vdslChanBadBlks OBJECT-TYPE
        SYNTAX        ZeroBasedCounter64
        UNITS         "blocks"
        MAX-ACCESS    read-only
        STATUS        current
        DESCRIPTION
            "Count of uncorrectable blocks since the unit was last
            reset."
        REFERENCE    "T1E1.4/2000-009R3, Part 1, common spec"
        ::= { vdslChanPerfDataEntry 4 }

    vdslChanCurr15MinTimeElapsed OBJECT-TYPE
        SYNTAX        HCPerfTimeElapsed
        UNITS         "seconds"
        MAX-ACCESS    read-only
        STATUS        current
        DESCRIPTION
            "Total elapsed seconds in this interval."
        ::= { vdslChanPerfDataEntry 5 }

    vdslChanCurr15MinFixedOctets OBJECT-TYPE
        SYNTAX        HCPerfCurrentCount
        UNITS         "octets"
        MAX-ACCESS    read-only
        STATUS        current
        DESCRIPTION
            "Count of corrected octets in this interval."
        REFERENCE    "T1E1.4/2000-009R3, Part 1, common spec"
        ::= { vdslChanPerfDataEntry 6 }

    vdslChanCurr15MinBadBlks OBJECT-TYPE
        SYNTAX        HCPerfCurrentCount
        UNITS         "blocks"
        MAX-ACCESS    read-only
        STATUS        current
        DESCRIPTION
            "Count of uncorrectable blocks in this interval."
        REFERENCE    "T1E1.4/2000-009R3, Part 1, common spec"
        ::= { vdslChanPerfDataEntry 7 }

    vdslChan1DayValidIntervals OBJECT-TYPE
        SYNTAX        HCPerfValidIntervals
        MAX-ACCESS    read-only
        STATUS        current
        DESCRIPTION
            "Valid Intervals per definition found in
            HC-PerfHist-TC-MIB."
        ::= { vdslChanPerfDataEntry 8 }

    vdslChan1DayInvalidIntervals OBJECT-TYPE
        SYNTAX        HCPerfInvalidIntervals
        MAX-ACCESS    read-only
        STATUS        current
        DESCRIPTION
            "Invalid Intervals per definition found in
            HC-PerfHist-TC-MIB."
        ::= { vdslChanPerfDataEntry 9 }

    vdslChanCurr1DayTimeElapsed OBJECT-TYPE
        SYNTAX       HCPerfTimeElapsed
        UNITS        "seconds"
        MAX-ACCESS   read-only
        STATUS       current
        DESCRIPTION
             "Number of seconds that have elapsed since the beginning
             of the current 1-day interval."
        ::= { vdslChanPerfDataEntry 10 }

    vdslChanCurr1DayFixedOctets OBJECT-TYPE
        SYNTAX        HCPerfCurrentCount
        UNITS         "octets"
        MAX-ACCESS    read-only
        STATUS        current
        DESCRIPTION
            "Count of corrected octets since the beginning of the
            current 1-day interval."
        REFERENCE    "T1E1.4/2000-009R3, Part 1, common spec"
        ::= { vdslChanPerfDataEntry 11 }

    vdslChanCurr1DayBadBlks OBJECT-TYPE
        SYNTAX        HCPerfCurrentCount
        UNITS         "blocks"
        MAX-ACCESS    read-only
        STATUS        current
        DESCRIPTION
            "Count of uncorrectable blocks since the beginning of the
            current 1-day interval."
        REFERENCE    "T1E1.4/2000-009R3, Part 1, common spec"
        ::= { vdslChanPerfDataEntry 12 }

    vdslChanIntervalTable       OBJECT-TYPE
        SYNTAX       SEQUENCE OF VdslChanIntervalEntry
        MAX-ACCESS   not-accessible
        STATUS       current
        DESCRIPTION
            "This table provides one row for each Vtu channel data
            collection interval.  VDSL channel interfaces are those
            ifEntries where ifType is equal to interleave(124) or
            fast(125)."
        ::= { vdslLineMgt 8 }

    vdslChanIntervalEntry OBJECT-TYPE
        SYNTAX        VdslChanIntervalEntry
        MAX-ACCESS    not-accessible
        STATUS        current
        DESCRIPTION
            "An entry in the vdslChanIntervalTable."
        INDEX { ifIndex,
                vdslPhysSide,
                vdslChanIntervalNumber }
        ::= { vdslChanIntervalTable 1 }

    VdslChanIntervalEntry ::=
        SEQUENCE
            {
            vdslChanIntervalNumber         Unsigned32,
            vdslChanIntervalFixedOctets    HCPerfIntervalCount,
            vdslChanIntervalBadBlks        HCPerfIntervalCount
            }

    vdslChanIntervalNumber OBJECT-TYPE
        SYNTAX        Unsigned32 (1..96)
        MAX-ACCESS    not-accessible
        STATUS        current
        DESCRIPTION
            "Performance Data Interval number 1 is the most recent
            previous interval; interval 96 is 24 hours ago.
            Intervals 2 to 96 are optional."
        ::= { vdslChanIntervalEntry 1 }

    vdslChanIntervalFixedOctets OBJECT-TYPE
        SYNTAX        HCPerfIntervalCount
        UNITS        "octets"
        MAX-ACCESS    read-only
        STATUS        current
        DESCRIPTION
            "Count of corrected octets in this interval."
        REFERENCE    "T1E1.4/2000-009R3, Part 1, common spec"
        ::= { vdslChanIntervalEntry 2 }

    vdslChanIntervalBadBlks OBJECT-TYPE
        SYNTAX        HCPerfIntervalCount
        UNITS        "blocks"
        MAX-ACCESS    read-only
        STATUS        current
        DESCRIPTION
            "Count of uncorrectable blocks in this interval."
        REFERENCE    "T1E1.4/2000-009R3, Part 1, common spec"
        ::= { vdslChanIntervalEntry 3 }

    vdslChan1DayIntervalTable OBJECT-TYPE
        SYNTAX       SEQUENCE OF VdslChan1DayIntervalEntry
        MAX-ACCESS   not-accessible
        STATUS       current
        DESCRIPTION
            "This table provides one row for each VDSL performance
            data collection interval.  This table contains live data
            from equipment.  As such, it is NOT persistent."
        ::= { vdslLineMgt 9 }

    vdslChan1DayIntervalEntry OBJECT-TYPE
        SYNTAX       VdslChan1DayIntervalEntry
        MAX-ACCESS   not-accessible
        STATUS       current
        DESCRIPTION
            "An entry in the vdslChan1DayIntervalTable."
        INDEX { ifIndex,
                vdslPhysSide,
                vdslChan1DayIntervalNumber }
        ::= { vdslChan1DayIntervalTable 1 }

    VdslChan1DayIntervalEntry ::=
        SEQUENCE
        {
        vdslChan1DayIntervalNumber         Unsigned32,
        vdslChan1DayIntervalMoniSecs       HCPerfTimeElapsed,
        vdslChan1DayIntervalFixedOctets    HCPerfCurrentCount,
        vdslChan1DayIntervalBadBlks        HCPerfCurrentCount
        }

    vdslChan1DayIntervalNumber OBJECT-TYPE
        SYNTAX       Unsigned32 (1..30)
        MAX-ACCESS   not-accessible
        STATUS       current
        DESCRIPTION
            "History Data Interval number.  Interval 1 is the most
            recent previous day; interval 30 is 30 days ago.  Intervals
            2 to 30 are optional."
        ::= { vdslChan1DayIntervalEntry 1 }

    vdslChan1DayIntervalMoniSecs OBJECT-TYPE
        SYNTAX       HCPerfTimeElapsed
        UNITS        "seconds"
        MAX-ACCESS   read-only
        STATUS       current
        DESCRIPTION
            "The amount of time in the 1-day interval over which the
            performance monitoring information is actually counted.
            This value will be the same as the interval duration except
            in a situation where performance monitoring data could not
            be collected for any reason."
        ::= { vdslChan1DayIntervalEntry 2 }

    vdslChan1DayIntervalFixedOctets OBJECT-TYPE
        SYNTAX        HCPerfCurrentCount
        UNITS        "octets"
        MAX-ACCESS    read-only
        STATUS        current
        DESCRIPTION
            "Count of corrected octets in this interval."
        REFERENCE    "T1E1.4/2000-009R3, Part 1, common spec"
        ::= { vdslChan1DayIntervalEntry 3 }

    vdslChan1DayIntervalBadBlks OBJECT-TYPE
        SYNTAX        HCPerfCurrentCount
        UNITS        "blocks"
        MAX-ACCESS    read-only
        STATUS        current
        DESCRIPTION
            "Count of uncorrectable blocks in this interval."
        REFERENCE    "T1E1.4/2000-009R3, Part 1, common spec"
        ::= { vdslChan1DayIntervalEntry 4 }

    --
    -- profile tables
    --

    vdslLineConfProfileTable OBJECT-TYPE
        SYNTAX         SEQUENCE OF VdslLineConfProfileEntry
        MAX-ACCESS     not-accessible
        STATUS         current
        DESCRIPTION
            "This table contains information on the VDSL line
            configuration.  One entry in this table reflects a
            profile defined by a manager which can be used to
            configure the VDSL line."
        ::= { vdslLineMgt 11 }

    vdslLineConfProfileEntry OBJECT-TYPE
        SYNTAX         VdslLineConfProfileEntry
        MAX-ACCESS     not-accessible
        STATUS         current
        DESCRIPTION
            "Each entry consists of a list of parameters that
            represents the configuration of a VDSL line.

            A default profile with an index of 'DEFVAL', will
            always exist and its parameters will be set to vendor
            specific values, unless otherwise specified in this
            document."
        INDEX { vdslLineConfProfileName }
        ::= { vdslLineConfProfileTable 1 }

    VdslLineConfProfileEntry ::=
        SEQUENCE
            {
            vdslLineConfProfileName            SnmpAdminString,
            vdslLineConfDownRateMode           INTEGER,
            vdslLineConfUpRateMode             INTEGER,
            vdslLineConfDownMaxPwr             Unsigned32,
            vdslLineConfUpMaxPwr               Unsigned32,
            vdslLineConfDownMaxSnrMgn          Unsigned32,
            vdslLineConfDownMinSnrMgn          Unsigned32,
            vdslLineConfDownTargetSnrMgn       Unsigned32,
            vdslLineConfUpMaxSnrMgn            Unsigned32,
            vdslLineConfUpMinSnrMgn            Unsigned32,
            vdslLineConfUpTargetSnrMgn         Unsigned32,
            vdslLineConfDownFastMaxDataRate    Unsigned32,
            vdslLineConfDownFastMinDataRate    Unsigned32,
            vdslLineConfDownSlowMaxDataRate    Unsigned32,
            vdslLineConfDownSlowMinDataRate    Unsigned32,
            vdslLineConfUpFastMaxDataRate      Unsigned32,
            vdslLineConfUpFastMinDataRate      Unsigned32,
            vdslLineConfUpSlowMaxDataRate      Unsigned32,
            vdslLineConfUpSlowMinDataRate      Unsigned32,
            vdslLineConfDownRateRatio          Unsigned32,
            vdslLineConfUpRateRatio            Unsigned32,
            vdslLineConfDownMaxInterDelay      Unsigned32,
            vdslLineConfUpMaxInterDelay        Unsigned32,
            vdslLineConfDownPboControl         INTEGER,
            vdslLineConfUpPboControl           INTEGER,
            vdslLineConfDownPboLevel           Unsigned32,
            vdslLineConfUpPboLevel             Unsigned32,
            vdslLineConfDeploymentScenario     INTEGER,
            vdslLineConfAdslPresence           INTEGER,
            vdslLineConfApplicableStandard     INTEGER,
            vdslLineConfBandPlan               INTEGER,
            vdslLineConfBandPlanFx             Unsigned32,
            vdslLineConfBandOptUsage           INTEGER,
            vdslLineConfUpPsdTemplate          INTEGER,
            vdslLineConfDownPsdTemplate        INTEGER,
            vdslLineConfHamBandMask            BITS,
            vdslLineConfCustomNotch1Start      Unsigned32,
            vdslLineConfCustomNotch1Stop       Unsigned32,
            vdslLineConfCustomNotch2Start      Unsigned32,
            vdslLineConfCustomNotch2Stop       Unsigned32,
            vdslLineConfDownTargetSlowBurst    Unsigned32,
            vdslLineConfUpTargetSlowBurst      Unsigned32,
            vdslLineConfDownMaxFastFec         Unsigned32,
            vdslLineConfUpMaxFastFec           Unsigned32,
            vdslLineConfLineType               INTEGER,
            vdslLineConfProfRowStatus          RowStatus
            }

    vdslLineConfProfileName OBJECT-TYPE
        SYNTAX       SnmpAdminString (SIZE (1..32))
        MAX-ACCESS   not-accessible
        STATUS       current
        DESCRIPTION
            "This object identifies a row in this table.

            A default profile with an index of 'DEFVAL', will
            always exist and its parameters will be set to vendor
            specific values, unless otherwise specified in this
            document."
        ::= { vdslLineConfProfileEntry 1 }

    vdslLineConfDownRateMode OBJECT-TYPE
        SYNTAX       INTEGER
                     {
                     manual(1),
                     adaptAtInit(2)
                     }
        MAX-ACCESS   read-create
        STATUS       current
        DESCRIPTION
            "Specifies the rate selection behavior for the line
            in the downstream direction.

            manual(1)       forces the rate to the configured rate
            adaptAtInit(2)  adapts the line based upon line quality."
        DEFVAL       { adaptAtInit }
        ::= { vdslLineConfProfileEntry 2 }

    vdslLineConfUpRateMode OBJECT-TYPE
        SYNTAX       INTEGER
                     {
                     manual(1),
                     adaptAtInit(2)
                     }
        MAX-ACCESS   read-create
        STATUS       current
        DESCRIPTION
            "Specifies the rate selection behavior for the line
            in the upstream direction.

            manual(1)       forces the rate to the configured rate
            adaptAtInit(2)  adapts the line based upon line quality."
        DEFVAL       { adaptAtInit }
        ::= { vdslLineConfProfileEntry 3 }

    vdslLineConfDownMaxPwr OBJECT-TYPE
        SYNTAX       Unsigned32 (0..58)
        UNITS        "0.25dBm"
        MAX-ACCESS   read-create
        STATUS       current
        DESCRIPTION
            "Specifies the maximum aggregate downstream power
            level in the range 0 to 14.5 dBm."
        REFERENCE    "T1E1.4/2000-009R3, Part 1, common spec"
        DEFVAL       { 0 }
        ::= { vdslLineConfProfileEntry 4 }

    vdslLineConfUpMaxPwr OBJECT-TYPE
        SYNTAX       Unsigned32 (0..58)
        UNITS        "0.25dBm"
        MAX-ACCESS   read-create
        STATUS       current
        DESCRIPTION
            "Specifies the maximum aggregate upstream power
            level in the range 0 to 14.5 dBm."
        REFERENCE    "T1E1.4/2000-009R3, Part 1, common spec"
        DEFVAL       { 0 }
        ::= { vdslLineConfProfileEntry 5 }

    vdslLineConfDownMaxSnrMgn OBJECT-TYPE
        SYNTAX       Unsigned32 (0..127)
        UNITS        "0.25dBm"
        MAX-ACCESS   read-create
        STATUS       current
        DESCRIPTION
            "Specifies the maximum downstream Signal/Noise Margin
            in units of 0.25 dB, for a range of 0 to 31.75 dB."
        REFERENCE    "T1E1.4/2000-009R3, Part 1, common spec"
        DEFVAL       { 0 }
        ::= { vdslLineConfProfileEntry 6 }

    vdslLineConfDownMinSnrMgn OBJECT-TYPE
        SYNTAX       Unsigned32 (0..127)
        UNITS        "0.25dBm"
        MAX-ACCESS   read-create
        STATUS       current
        DESCRIPTION
            "Specifies the minimum downstream Signal/Noise Margin
            in units of 0.25 dB, for a range of 0 to 31.75 dB."
        REFERENCE    "T1E1.4/2000-009R3, Part 1, common spec"
        DEFVAL       { 0 }
        ::= { vdslLineConfProfileEntry 7 }

    vdslLineConfDownTargetSnrMgn OBJECT-TYPE
        SYNTAX       Unsigned32 (0..127)
        UNITS        "0.25dBm"
        MAX-ACCESS   read-create
        STATUS       current
        DESCRIPTION
            "Specifies the target downstream Signal/Noise Margin
            in units of 0.25 dB, for a range of 0 to 31.75 dB.
            This is the Noise Margin the transceivers must achieve
            with a BER of 10^-7 or better to successfully complete
            initialization."
        REFERENCE    "T1E1.4/2000-009R3, Part 1, common spec"
        DEFVAL       { 0 }
        ::= { vdslLineConfProfileEntry 8 }

    vdslLineConfUpMaxSnrMgn OBJECT-TYPE
        SYNTAX       Unsigned32 (0..127)
        UNITS        "0.25dBm"
        MAX-ACCESS   read-create
        STATUS       current
        DESCRIPTION
            "Specifies the maximum upstream Signal/Noise Margin
            in units of 0.25 dB, for a range of 0 to 31.75 dB."
        REFERENCE    "T1E1.4/2000-009R3, Part 1, common spec"
        DEFVAL       { 0 }
        ::= { vdslLineConfProfileEntry 9 }

    vdslLineConfUpMinSnrMgn OBJECT-TYPE
        SYNTAX       Unsigned32 (0..127)
        UNITS        "0.25dBm"
        MAX-ACCESS   read-create
        STATUS       current
        DESCRIPTION
            "Specifies the minimum upstream Signal/Noise Margin
            in units of 0.25 dB, for a range of 0 to 31.75 dB."
        REFERENCE    "T1E1.4/2000-009R3, Part 1, common spec"
        DEFVAL       { 0 }
        ::= { vdslLineConfProfileEntry 10 }

    vdslLineConfUpTargetSnrMgn OBJECT-TYPE
        SYNTAX       Unsigned32 (0..127)
        UNITS        "0.25dBm"
        MAX-ACCESS   read-create
        STATUS       current
        DESCRIPTION
            "Specifies the target upstream Signal/Noise Margin in
            units of 0.25 dB, for a range of 0 to 31.75 dB.  This
            is the Noise Margin the transceivers must achieve with
            a BER of 10^-7 or better to successfully complete
            initialization."
        REFERENCE    "T1E1.4/2000-009R3, Part 1, common spec"
        DEFVAL       { 0 }
        ::= { vdslLineConfProfileEntry 11 }

    vdslLineConfDownFastMaxDataRate OBJECT-TYPE
        SYNTAX       Unsigned32
        UNITS        "kbps"
        MAX-ACCESS   read-create
        STATUS       current
        DESCRIPTION
            "Specifies the maximum downstream fast channel
            data rate in steps of 1000 bits/second."
        DEFVAL       { 0 }
        ::= { vdslLineConfProfileEntry 12 }

    vdslLineConfDownFastMinDataRate OBJECT-TYPE
        SYNTAX       Unsigned32
        UNITS        "kbps"
        MAX-ACCESS   read-create
        STATUS       current
        DESCRIPTION
            "Specifies the minimum downstream fast channel
            data rate in steps of 1000 bits/second."
        DEFVAL       { 0 }
        ::= { vdslLineConfProfileEntry 13 }

    vdslLineConfDownSlowMaxDataRate OBJECT-TYPE
        SYNTAX       Unsigned32
        UNITS        "kbps"
        MAX-ACCESS   read-create
        STATUS       current
        DESCRIPTION
            "Specifies the maximum downstream slow channel
            data rate in steps of 1000 bits/second.

            The maximum aggregate downstream transmit speed
            of the line can be derived from the sum of maximum
            downstream fast and slow channel data rates."
        DEFVAL       { 0 }
        ::= { vdslLineConfProfileEntry 14 }

    vdslLineConfDownSlowMinDataRate OBJECT-TYPE
        SYNTAX       Unsigned32
        UNITS        "kbps"
        MAX-ACCESS   read-create
        STATUS       current
        DESCRIPTION
            "Specifies the minimum downstream slow channel
            data rate in steps of 1000 bits/second.

            The minimum aggregate downstream transmit speed
            of the line can be derived from the sum of minimum
            downstream fast and slow channel data rates."
        DEFVAL       { 0 }
        ::= { vdslLineConfProfileEntry 15 }

    vdslLineConfUpFastMaxDataRate OBJECT-TYPE
        SYNTAX       Unsigned32
        UNITS        "kbps"
        MAX-ACCESS   read-create
        STATUS       current
        DESCRIPTION
            "Specifies the maximum upstream fast channel
            data rate in steps of 1000 bits/second.

            The maximum aggregate upstream transmit speed
            of the line can be derived from the sum of maximum
            upstream fast and slow channel data rates."
        DEFVAL       { 0 }
        ::= { vdslLineConfProfileEntry 16 }

    vdslLineConfUpFastMinDataRate OBJECT-TYPE
        SYNTAX       Unsigned32
        UNITS        "kbps"
        MAX-ACCESS   read-create
        STATUS       current
        DESCRIPTION
            "Specifies the minimum upstream fast channel
            data rate in steps of 1000 bits/second.

            The minimum aggregate upstream transmit speed
            of the line can be derived from the sum of minimum
            upstream fast and slow channel data rates."
        DEFVAL       { 0 }
        ::= { vdslLineConfProfileEntry 17 }

    vdslLineConfUpSlowMaxDataRate OBJECT-TYPE
        SYNTAX       Unsigned32
        UNITS        "kbps"
        MAX-ACCESS   read-create
        STATUS       current
        DESCRIPTION
            "Specifies the maximum upstream slow channel
            data rate in steps of 1000 bits/second."
        DEFVAL       { 0 }
        ::= { vdslLineConfProfileEntry 18 }

    vdslLineConfUpSlowMinDataRate OBJECT-TYPE
        SYNTAX       Unsigned32
        UNITS        "kbps"
        MAX-ACCESS   read-create
        STATUS       current
        DESCRIPTION
            "Specifies the minimum upstream slow channel
            data rate in steps of 1000 bits/second."
        DEFVAL       { 0 }
        ::= { vdslLineConfProfileEntry 19 }

    vdslLineConfDownRateRatio OBJECT-TYPE
        SYNTAX       Unsigned32 (0..100)
        UNITS        "percent"
        MAX-ACCESS   read-create
        STATUS       current
        DESCRIPTION
            "For dynamic rate adaptation at startup, the allocation
            of data rate in excess of the minimum data rate for each
            channel is controlled by the object.  This object specifies
            the ratio of the allocation of the excess data rate between
            the fast and the slow channels.  This allocation represents
            downstream Fast Channel Allocation / Slow Channel
            Allocation."
        DEFVAL       { 0 }
        ::= { vdslLineConfProfileEntry 20 }

    vdslLineConfUpRateRatio OBJECT-TYPE
        SYNTAX       Unsigned32 (0..100)
        UNITS        "percent"
        MAX-ACCESS   read-create
        STATUS       current
        DESCRIPTION
            "For dynamic rate adaptation at startup, the allocation
            of data rate in excess of the minimum data rate for each
            channel is controlled by the object.  This object specifies
            the ratio of the allocation of the excess data rate between
            the fast and the slow channels.  This allocation represents
            upstream Fast Channel Allocation/Slow Channel Allocation."
        DEFVAL       { 0 }
        ::= { vdslLineConfProfileEntry 21 }

    vdslLineConfDownMaxInterDelay OBJECT-TYPE
        SYNTAX       Unsigned32 (0..255)
        UNITS        "milliseconds"
        MAX-ACCESS   read-create
        STATUS       current
        DESCRIPTION
            "Specifies the maximum interleave delay for the
            downstream slow channel."
        DEFVAL       { 0 }
        ::= { vdslLineConfProfileEntry 22 }

    vdslLineConfUpMaxInterDelay OBJECT-TYPE
        SYNTAX       Unsigned32 (0..255)
        UNITS        "milliseconds"
        MAX-ACCESS   read-create
        STATUS       current
        DESCRIPTION
            "Specifies the maximum interleave delay for the
            upstream slow channel."
        DEFVAL       { 0 }
        ::= { vdslLineConfProfileEntry 23 }

    vdslLineConfDownPboControl OBJECT-TYPE
        SYNTAX       INTEGER
                     {
                     disabled(1),
                     auto(2),
                     manual(3)
                     }
        MAX-ACCESS   read-create
        STATUS       current
        DESCRIPTION
            "Downstream power backoff (PBO) control for this
            line.  For transceivers which do not support downstream
            PBO control, this object MUST be fixed at disabled(1).
            If auto(2) is selected, the transceiver will automatically
            adjust the power backoff.  If manual(3) is selected,
            then the transceiver will use the value from
            vdslLineConfDownPboLevel."
        DEFVAL       { disabled }
        ::= { vdslLineConfProfileEntry 24 }

    vdslLineConfUpPboControl OBJECT-TYPE
        SYNTAX       INTEGER
                     {
                     disabled(1),
                     auto(2),
                     manual(3)
                     }
        MAX-ACCESS   read-create
        STATUS       current
        DESCRIPTION
            "Upstream power backoff (PBO) control for this
            line.  For transceivers which do not support upstream
            PBO control, this object MUST be fixed at disabled(1).
            If auto(2) is selected, the transceiver will automatically
            adjust the power backoff.  If manual(3) is selected,
            then the transceiver will use the value from
            vdslLineConfUpPboLevel."
        DEFVAL       { disabled }
        ::= { vdslLineConfProfileEntry 25 }

    vdslLineConfDownPboLevel OBJECT-TYPE
        SYNTAX       Unsigned32 (0..160)
        UNITS        "0.25dB"
        MAX-ACCESS   read-create
        STATUS       current
        DESCRIPTION
            "Specifies the downstream backoff level to be used
            when vdslLineConfDownPboControl = manual(3)."
        DEFVAL       { 0 }
        ::= { vdslLineConfProfileEntry 26 }

    vdslLineConfUpPboLevel OBJECT-TYPE
        SYNTAX       Unsigned32 (0..160)
        UNITS        "0.25dB"
        MAX-ACCESS   read-create
        STATUS       current
        DESCRIPTION
            "Specifies the upstream backoff level to be used
            when vdslLineConfUpPboControl = manual(3)."
        DEFVAL       { 0 }
        ::= { vdslLineConfProfileEntry 27 }

    vdslLineConfDeploymentScenario OBJECT-TYPE
        SYNTAX       INTEGER
                     {
                     fttCab(1),
                     fttEx(2),
                     other(3)
                     }
        MAX-ACCESS   read-create
        STATUS       current
        DESCRIPTION
            "The VDSL line deployment scenario.  When using
            fttCab(1), the VTU-C is located in a street cabinet.
            When using fttEx(2), the VTU-C is located at the
            central office.  Changes to this value will have
            no effect on the transceiver."
        REFERENCE    "DSL Forum TR-057"
        DEFVAL       { fttCab }
        ::= { vdslLineConfProfileEntry 28 }

    vdslLineConfAdslPresence OBJECT-TYPE
        SYNTAX       INTEGER
                     {
                     none(1),
                     adslOverPots(2),
                     adslOverISDN(3)
                     }
        MAX-ACCESS   read-create
        STATUS       current
        DESCRIPTION
            "Indicates presence of ADSL service in the associated
            cable bundle/binder.

            none(1)         indicates no ADSL service in the bundle
            adslOverPots(2) indicates ADSL service over POTS is
                            present in the bundle
            adslOverISDN(3) indicates ADSL service over ISDN is
                            present in the bundle"
        DEFVAL       { none }
        ::= { vdslLineConfProfileEntry 29 }

    vdslLineConfApplicableStandard OBJECT-TYPE
        SYNTAX       INTEGER
                     {
                     ansi(1),
                     etsi(2),
                     itu(3),
                     other(4)
                     }
        MAX-ACCESS   read-create
        STATUS       current
        DESCRIPTION
            "The VDSL standard to be used for the line.

             ansi(1)      indicates ANSI standard
             etsi(2)      indicates ETSI standard
             itu(3)       indicates ITU standard
             other(4)     indicates a standard other than the above."
        DEFVAL       { ansi }
        ::= { vdslLineConfProfileEntry 30 }

    vdslLineConfBandPlan OBJECT-TYPE
        SYNTAX       INTEGER
                     {
                     bandPlan997(1),
                     bandPlan998(2),
                     bandPlanFx(3),
                     other(4)
                     }
        MAX-ACCESS   read-create
        STATUS       current
        DESCRIPTION
            "The VDSL band plan to be used for the line.

             bandPlan997(1) is to be used for
                  ITU-T G.993.1 Bandplan-B
                  ETSI Bandplan
                  ANSI Plan 997

             bandPlan998(2) is to be used for
                  ITU-T G.993.1 Bandplan-A
                  ANSI Plan 998

             bandPlanFx(3) is to be used for
                  ITU-T G.993.1 Bandplan-C.

             other(4) is to be used for
                  non-standard bandplans.

             If this object is set to bandPlanFx(3), then the
             object vdslLineConfBandPlanFx MUST also be set."
        DEFVAL       { bandPlan997 }
        ::= { vdslLineConfProfileEntry 31 }

    vdslLineConfBandPlanFx OBJECT-TYPE
        SYNTAX       Unsigned32 (3750..12000)
        UNITS        "kHz"
        MAX-ACCESS   read-create
        STATUS       current
        DESCRIPTION
            "The frequency limit between bands D2 and U2 when
            vdslLineConfBandPlan is set to bandPlanFx(3)."
        DEFVAL       { 3750 }
        ::= { vdslLineConfProfileEntry 32 }

    vdslLineConfBandOptUsage OBJECT-TYPE
        SYNTAX       INTEGER
                     {
                     unused(1),
                     upstream(2),
                     downstream(3)
                     }
        MAX-ACCESS   read-create
        STATUS       current
        DESCRIPTION
            "Defines the VDSL link use of the optional frequency
            range [25kHz - 138kHz] (Opt).

            unused(1)     indicates Opt is unused
            upstream(2)   indicates Opt usage is for upstream
            downstream(3) indicates Opt usage is for downstream."
        REFERENCE    "ITU-T G.993.1, section 6.1"
        DEFVAL       { unused }
        ::= { vdslLineConfProfileEntry 33 }

    vdslLineConfUpPsdTemplate OBJECT-TYPE
        SYNTAX       INTEGER
                     {
                     templateMask1(1),
                     templateMask2(2)
                     }
        MAX-ACCESS   read-create
        STATUS       current
        DESCRIPTION
            "The upstream PSD template to be used for the line.
            Here, templateMask1(1) refers to a notched mask that
            limits the transmitted PSD within the internationally
            standardized HAM (Handheld Amateur Radio) radio bands,
            while templateMask2(2) refers to an unnotched mask.

            The masks themselves depend upon the applicable
            standard being used (vdslLineConfApplicableStandard)."
        REFERENCE    "DSL TR-057"
        DEFVAL       { templateMask1 }
        ::= { vdslLineConfProfileEntry 34 }

    vdslLineConfDownPsdTemplate OBJECT-TYPE
        SYNTAX       INTEGER
                     {
                     templateMask1(1),
                     templateMask2(2)
                     }
        MAX-ACCESS   read-create
        STATUS       current
        DESCRIPTION
            "The downstream PSD template to be used for the line.
            Here, templateMask1(1) refers to a notched mask that
            limits the transmitted PSD within the internationally
            standardized HAM (Handheld Amateur Radio) radio bands,
            while templateMask2(2) refers to an unnotched mask.

            The masks themselves depend upon the applicable
            standard being used (vdslLineConfApplicableStandard)."
        REFERENCE    "DSL TR-057"
        DEFVAL       { templateMask1 }
        ::= { vdslLineConfProfileEntry 35 }

    vdslLineConfHamBandMask OBJECT-TYPE
        SYNTAX       BITS
            {
            customNotch1(0),     -- custom (region-specific) notch
            customNotch2(1),     -- custom (region-specific) notch
            amateurBand30m(2),   -- amateur radio band notch
            amateurBand40m(3),   -- amateur radio band notch
            amateurBand80m(4),   -- amateur radio band notch
            amateurBand160m(5)   -- amateur radio band notch
            }
        MAX-ACCESS   read-create
        STATUS       current
        DESCRIPTION
            "The transmit power spectral density mask code, used
            to avoid interference with HAM (Handheld Amateur Radio)
            radio bands by introducing power control (notching) in one
            or more of these bands.

            Amateur radio band notching is defined in the VDSL
            spectrum as follows:

            Band  Start Frequency     Stop Frequency
            ----  ------------------  --------------------------------
            30m   1810 kHz            2000 kHz
            40m   3500 kHz            3800 kHz (ETSI); 4000 kHz (ANSI)
            80m   7000 kHz            7100 kHz (ETSI); 7300 kHz (ANSI)
            160m  10100 kHz           10150 kHz

            Notching for each standard band can be enabled or disabled
            via the bit mask.

            Two custom notches may be specified.  If either of these
            are enabled via the bit mask, then the following objects
            MUST be specified:

            If customNotch1 is enabled, then both
                vdslLineConfCustomNotch1Start
                vdslLineConfCustomNotch1Stop
            MUST be specified.

            If customNotch2 is enabled, then both
                vdslLineConfCustomNotch2Start
                vdslLineConfCustomNotch2Stop
            MUST be specified."
        REFERENCE    "DSLF TR-057, section 2.6"
        DEFVAL       { { } }
        ::= { vdslLineConfProfileEntry 36 }

    vdslLineConfCustomNotch1Start OBJECT-TYPE
        SYNTAX       Unsigned32
        UNITS        "kHz"
        MAX-ACCESS   read-create
        STATUS       current
        DESCRIPTION
            "Specifies the start frequency of custom HAM (Handheld
            Amateur Radio) notch 1.  vdslLineConfCustomNotch1Start MUST
            be less than or equal to vdslLineConfCustomNotch1Stop."
        DEFVAL       { 0 }
        ::= { vdslLineConfProfileEntry 37 }

    vdslLineConfCustomNotch1Stop OBJECT-TYPE
        SYNTAX       Unsigned32
        UNITS        "kHz"
        MAX-ACCESS   read-create
        STATUS       current
        DESCRIPTION
            "Specifies the stop frequency of custom HAM (Handheld
            Amateur Radio) notch 1.  vdslLineConfCustomNotch1Stop MUST
            be greater than or equal to vdslLineConfCustomNotch1Start."
        DEFVAL       { 0 }
        ::= { vdslLineConfProfileEntry 38 }

    vdslLineConfCustomNotch2Start OBJECT-TYPE
        SYNTAX       Unsigned32
        UNITS        "kHz"
        MAX-ACCESS   read-create
        STATUS       current
        DESCRIPTION
            "Specifies the start frequency of custom HAM (Handheld
            Amateur Radio) notch 2.  vdslLineConfCustomNotch2Start MUST
            be less than or equal to vdslLineConfCustomNotch2Stop."
        DEFVAL       { 0 }
        ::= { vdslLineConfProfileEntry 39 }

    vdslLineConfCustomNotch2Stop OBJECT-TYPE
        SYNTAX       Unsigned32
        UNITS        "kHz"
        MAX-ACCESS   read-create
        STATUS       current
        DESCRIPTION
            "Specifies the stop frequency of custom HAM (Handheld
            Amateur Radio) notch 2.  vdslLineConfCustomNotch2Stop MUST
            be greater than or equal to vdslLineConfCustomNotch2Stop."
        DEFVAL       { 0 }
        ::= { vdslLineConfProfileEntry 40 }

    vdslLineConfDownTargetSlowBurst OBJECT-TYPE
        SYNTAX       Unsigned32 (0..1275)
        UNITS        "microseconds"
        MAX-ACCESS   read-create
        STATUS       current
        DESCRIPTION
            "Specifies the target level of impulse noise (burst)
            protection for an interleaved (slow) channel."
        REFERENCE    "ITU-T G.997.1, section 7.3.2.3"
        DEFVAL       { 0 }
        ::= { vdslLineConfProfileEntry 41 }

    vdslLineConfUpTargetSlowBurst OBJECT-TYPE
        SYNTAX       Unsigned32 (0..1275)
        UNITS        "microseconds"
        MAX-ACCESS   read-create
        STATUS       current
        DESCRIPTION
            "Specifies the target level of impulse noise (burst)
            protection for an interleaved (slow) channel."
        REFERENCE    "ITU-T G.997.1, section 7.3.2.3"
        DEFVAL       { 0 }
        ::= { vdslLineConfProfileEntry 42 }

    vdslLineConfDownMaxFastFec OBJECT-TYPE
        SYNTAX       Unsigned32 (0..50)
        UNITS        "%"
        MAX-ACCESS   read-create
        STATUS       current
        DESCRIPTION
            "This parameter provisions the maximum level of Forward
            Error Correction (FEC) redundancy related overhead to
            be maintained for a fast channel."
        DEFVAL       { 0 }
        ::= { vdslLineConfProfileEntry 43 }

    vdslLineConfUpMaxFastFec OBJECT-TYPE
        SYNTAX       Unsigned32 (0..50)
        UNITS        "%"
        MAX-ACCESS   read-create
        STATUS       current
        DESCRIPTION
            "This parameter provisions the maximum level of Forward
            Error Correction (FEC) redundancy related overhead to
            be maintained for a fast channel."
        DEFVAL       { 0 }
        ::= { vdslLineConfProfileEntry 44 }

    vdslLineConfLineType OBJECT-TYPE
        SYNTAX       INTEGER
            {
            noChannel(1),         -- no channels exist
            fastOnly(2),          -- only fast channel exists
            interleavedOnly(3),   -- only interleaved channel exists
            fastOrInterleaved(4), -- either fast or interleaved channel
                                  -- exist, but only one at a time
            fastAndInterleaved(5) -- both fast and interleaved channels
                                  -- exist
            }
        MAX-ACCESS   read-create
        STATUS       current
        DESCRIPTION
            "This parameter provisions the VDSL physical entity at
            start-up by defining whether and how the line will be
            channelized, i.e. which channel type(s) are supported.
            If the line is to be channelized, the value will be other
            than noChannel(1).

            This configuration can be activated only during start-up.
            Afterwards, the value of vdslLineType coincides with the
            value of vdslLineConfLineType.  Depending on this vlaue,
            the corresponding entries in the ifTable for the
            interleaved and the fast channels are enabled or disabled
            according to the value of their ifOperStatus.

            Defined values are:

            noChannel(1)          -- no channels exist
            fastOnly(2)           -- only the fast channel exists
            interleavedOnly(3)    -- only the interleaved channel exists
            fastOrInterleaved(4)  -- either the fast or the interleaved
                                  -- channel exists, but only one at a
                                  -- time
            fastAndInterleaved(5) -- both fast and interleaved channels
                                  -- exist

            Note that 'slow' and 'interleaved' refer to the same
            channel."
        REFERENCE    "T1E1.4/2000-009R3, Part 1, common spec"
        DEFVAL       { noChannel }
        ::= { vdslLineConfProfileEntry 45 }

    vdslLineConfProfRowStatus OBJECT-TYPE
        SYNTAX       RowStatus
        MAX-ACCESS   read-create
        STATUS       current
        DESCRIPTION
            "This object is used to create a new row or modify or
            delete an existing row in this table.

            A profile activated by setting this object to 'active'.
            When 'active' is set, the system will validate the profile.

            Before a profile can be deleted or taken out of
            service, (by setting this object to 'destroy' or
            'outOfService') it must be first unreferenced
            from all associated lines."
        ::= { vdslLineConfProfileEntry 46 }

--vdslLinePrivateConfProfileTable

    vdslLinePrivateConfProfileTable OBJECT-TYPE
        SYNTAX         SEQUENCE OF VdslLinePrivateConfProfileEntry
        MAX-ACCESS     not-accessible
        STATUS         current
        DESCRIPTION
            "This table contains information on the VDSL line
            configuration.  One entry in this table reflects a
            profile defined by a manager which can be used to
            configure the VDSL line."
        ::= { vdslLineMgt 12 }

    vdslLinePrivateConfProfileEntry OBJECT-TYPE
        SYNTAX         VdslLinePrivateConfProfileEntry
        MAX-ACCESS     not-accessible
        STATUS         current
        DESCRIPTION
            "Each entry consists of a list of parameters that
            represents the configuration of a VDSL line.

            A default profile with an index of 'DEFVAL', will
            always exist and its parameters will be set to vendor
            specific values, unless otherwise specified in this
            document."
        INDEX { vdslLinePrivateConfProfileName }
        ::= { vdslLinePrivateConfProfileTable 1 }

    VdslLinePrivateConfProfileEntry ::=  SEQUENCE
            {
            vdslLinePrivateConfProfileName                  SnmpAdminString,
            vdslLinePrivateConfProfileDown1CenterFrequency  Integer32,
            vdslLinePrivateConfProfileDown2CenterFrequency  Integer32,
            vdslLinePrivateConfProfileUp1CenterFrequency    Integer32,
            vdslLinePrivateConfProfileUp2CenterFrequency    Integer32,
            vdslLinePrivateConfProfileDown1Constellation    Integer32,
            vdslLinePrivateConfProfileDown2Constellation    Integer32,
            vdslLinePrivateConfProfileUp1Constellation      Integer32,
            vdslLinePrivateConfProfileUp2Constellation      Integer32,
            vdslLinePrivateConfProfileDown1SymbolRate       Integer32,
            vdslLinePrivateConfProfileDown2SymbolRate       Integer32,
            vdslLinePrivateConfProfileUp1SymbolRate         Integer32,
            vdslLinePrivateConfProfileUp2SymbolRate         Integer32,
            vdslLinePrivateConfProfileDown1PsdLevel         Integer32,
            vdslLinePrivateConfProfileDown2PsdLevel         Integer32,
            vdslLinePrivateConfProfileUp1PsdLevel           Integer32,
            vdslLinePrivateConfProfileUp2PsdLevel           Integer32,
            vdslLinePrivateConfProfileDsMValue              Integer32,
            vdslLinePrivateConfProfileDsIValue              Integer32,
            vdslLinePrivateConfProfileUsMValue              Integer32,
            vdslLinePrivateConfProfileUsIValue              Integer32,
            vdslLinePrivateConfProfilePboStatus             EnabledStatus,
            vdslLinePrivateConfProfileRateAdapt             EnabledStatus,
            vdslLinePrivateConfProfileDsSnrMgn              Integer32,
            vdslLinePrivateConfProfileUsSnrMgn              Integer32,
            vdslLinePrivateConfProfileHamBandMask           BITS,
            vdslLinePrivateConfProfileLineType              INTEGER,
            vdslLinePrivateConfProfileRowStatus             RowStatus
            }

    vdslLinePrivateConfProfileName OBJECT-TYPE
        SYNTAX       SnmpAdminString (SIZE (1..32))
        MAX-ACCESS   not-accessible
        STATUS       current
        DESCRIPTION
            "This object identifies a row in this table.

            A default profile with an index of 'DEFVAL', will
            always exist and its parameters will be set to vendor
            specific values, unless otherwise specified in this
            document."
        ::= { vdslLinePrivateConfProfileEntry 1 }

    vdslLinePrivateConfProfileDown1CenterFrequency OBJECT-TYPE
        SYNTAX       Integer32 (0..'FFFF'h)
        UNITS        "33.75 kHz"
        MAX-ACCESS   read-write
        STATUS       current
        DESCRIPTION
            "The down 1 center frequency.
            Please note that the unit is in 33.75 kHz."
        ::= { vdslLinePrivateConfProfileEntry 2 }

    vdslLinePrivateConfProfileDown2CenterFrequency OBJECT-TYPE
        SYNTAX       Integer32 (0..'FFFF'h)
        UNITS        "33.75 kHz"
        MAX-ACCESS   read-write
        STATUS       current
        DESCRIPTION
            "The down 2 center frequency.
            Please note that the unit is in 33.75 kHz."
        ::= { vdslLinePrivateConfProfileEntry 3 }

    vdslLinePrivateConfProfileUp1CenterFrequency OBJECT-TYPE
        SYNTAX       Integer32 (0..'FFFF'h)
        UNITS        "33.75 kHz"
        MAX-ACCESS   read-write
        STATUS       current
        DESCRIPTION
            "The up 1 center frequency.
            Please note that the unit is in 33.75 kHz."
        ::= { vdslLinePrivateConfProfileEntry 4 }

    vdslLinePrivateConfProfileUp2CenterFrequency  OBJECT-TYPE
        SYNTAX       Integer32 (0..'FFFF'h)
        UNITS        "33.75 kHz"
        MAX-ACCESS   read-write
        STATUS       current
        DESCRIPTION
            "The up 2 center frequency.
             Please note that the unit is in 33.75 kHz."
        ::= { vdslLinePrivateConfProfileEntry 5 }

    vdslLinePrivateConfProfileDown1Constellation  OBJECT-TYPE
        SYNTAX       Integer32 (0..'FF'h)
        MAX-ACCESS   read-write
        STATUS       current
        DESCRIPTION
            "The down 1 Constellation, a power of 2
             to define the first downstream QAM (QAM = 2^CONSTELATION_DS1).
             Set this object to 0 to disable the down 1 constellation."
        ::= { vdslLinePrivateConfProfileEntry 6 }

    vdslLinePrivateConfProfileDown2Constellation  OBJECT-TYPE
        SYNTAX       Integer32 (0..'FF'h)
        MAX-ACCESS   read-write
        STATUS       current
        DESCRIPTION
            "The down 2 Constellation, a power of 2
             to define the second downstream QAM (QAM = 2^CONSTELATION_DS2).
             Set this object to 0 to disable the down 2 constellation."
        ::= { vdslLinePrivateConfProfileEntry 7 }

    vdslLinePrivateConfProfileUp1Constellation  OBJECT-TYPE
        SYNTAX       Integer32 (0..'FF'h)
        MAX-ACCESS   read-write
        STATUS       current
        DESCRIPTION
            "The up 1 Constellation, a power of 2
             to define the first downstream QAM (QAM = 2^CONSTELATION_US1).
             Set this object to 0 to disable the up 1 constellation."
        ::= { vdslLinePrivateConfProfileEntry 8 }

    vdslLinePrivateConfProfileUp2Constellation OBJECT-TYPE
        SYNTAX       Integer32 (0..'FF'h)
        MAX-ACCESS   read-write
        STATUS       current
        DESCRIPTION
            "The up 2 Constellation, a power of 2
             to define the second downstream QAM (QAM = 2^CONSTELATION_US2).
             Set this object to 0 to disable the up 2 constellation."
        ::= { vdslLinePrivateConfProfileEntry 9 }

    vdslLinePrivateConfProfileDown1SymbolRate  OBJECT-TYPE
        SYNTAX       Integer32 (0..'FF'h)
        UNITS        "67.5 kHz"
        MAX-ACCESS   read-write
        STATUS       current
        DESCRIPTION
            "The down 1 symbol rate.
             Set this object to 0 to disable the down 1 symbol rate.
             Please note that the unit is in 67.5 kHz."
        ::= { vdslLinePrivateConfProfileEntry 10 }

    vdslLinePrivateConfProfileDown2SymbolRate  OBJECT-TYPE
        SYNTAX       Integer32 (0..'FF'h)
        UNITS        "67.5 kHz"
        MAX-ACCESS   read-write
        STATUS       current
        DESCRIPTION
            "The down 2 symbol rate.
             Set this object to 0 to disable the down 2 symbol rate.
             Please note that the unit is in 67.5 kHz."
        ::= { vdslLinePrivateConfProfileEntry 11 }

    vdslLinePrivateConfProfileUp1SymbolRate OBJECT-TYPE
        SYNTAX       Integer32 (0..'FF'h)
        UNITS        "67.5 kHz"
        MAX-ACCESS   read-write
        STATUS       current
        DESCRIPTION
            "The up 1 symbol rate.
             Set this object to 0 to disable the up 1 symbol rate.
             Please note that the unit is in 67.5 kHz."
        ::= { vdslLinePrivateConfProfileEntry 12 }

    vdslLinePrivateConfProfileUp2SymbolRate OBJECT-TYPE
        SYNTAX       Integer32 (0..'FF'h)
        UNITS        "67.5 kHz"
        MAX-ACCESS   read-write
        STATUS       current
        DESCRIPTION
            "The up 2 symbol rate.
             Set this object to 0 to disable the up 2 symbol rate.
             Please note that the unit is in 67.5 kHz."
        ::= { vdslLinePrivateConfProfileEntry 13 }

    vdslLinePrivateConfProfileDown1PsdLevel OBJECT-TYPE
        SYNTAX       Integer32 (0..'FF'h)
        UNITS        "0.25 dBm/Hz"
        MAX-ACCESS   read-write
        STATUS       current
        DESCRIPTION
            "The down 1 power spectral density level.
             Please note that the unit is in 0.25 dBm/Hz."
        ::= { vdslLinePrivateConfProfileEntry 14 }

    vdslLinePrivateConfProfileDown2PsdLevel OBJECT-TYPE
        SYNTAX       Integer32 (0..'FF'h)
        UNITS        "0.25 dBm/Hz"
        MAX-ACCESS   read-write
        STATUS       current
        DESCRIPTION
            "The down 2 power spectral density level.
             Please note that the unit is in 0.25 dBm/Hz."
        ::= { vdslLinePrivateConfProfileEntry 15 }

    vdslLinePrivateConfProfileUp1PsdLevel OBJECT-TYPE
        SYNTAX       Integer32 (0..'FF'h)
        UNITS        "0.25 dBm/Hz"
        MAX-ACCESS   read-write
        STATUS       current
        DESCRIPTION
            "The up 1 power spectral density level.
             Please note that the unit is in 0.25 dBm/Hz."
        ::= { vdslLinePrivateConfProfileEntry 16 }

    vdslLinePrivateConfProfileUp2PsdLevel OBJECT-TYPE
        SYNTAX       Integer32 (0..'FF'h)
        UNITS        "0.25 dBm/Hz"
        MAX-ACCESS   read-write
        STATUS       current
        DESCRIPTION
            "The up 2 power spectral density level.
             Please note that the unit is in 0.25 dBm/Hz."
        ::= { vdslLinePrivateConfProfileEntry 17 }

    vdslLinePrivateConfProfileDsMValue OBJECT-TYPE
        SYNTAX       Integer32 (0..64)
        MAX-ACCESS   read-write
        STATUS       current
        DESCRIPTION
            "The downstream interleaving depth index value.
             Set this object to 0 means interleaver OFF."
        ::= { vdslLinePrivateConfProfileEntry 18 }

    vdslLinePrivateConfProfileDsIValue OBJECT-TYPE
        SYNTAX       Integer32 (4|8)
        MAX-ACCESS   read-write
        STATUS       current
        DESCRIPTION
            "The downstream interleaving block length value."
        ::= { vdslLinePrivateConfProfileEntry 19 }

    vdslLinePrivateConfProfileUsMValue  OBJECT-TYPE
        SYNTAX       Integer32 (0..64)
        MAX-ACCESS   read-write
        STATUS       current
        DESCRIPTION
            "The upstream interleaving depth index value.
             Set this object to 0 means interleaver OFF."
        ::= { vdslLinePrivateConfProfileEntry 20 }

    vdslLinePrivateConfProfileUsIValue  OBJECT-TYPE
        SYNTAX       Integer32 (4|8)
        MAX-ACCESS   read-write
        STATUS       current
        DESCRIPTION
            "The upstream interleaving block length value."
        ::= { vdslLinePrivateConfProfileEntry 21 }

    vdslLinePrivateConfProfilePboStatus  OBJECT-TYPE
        SYNTAX       EnabledStatus
        MAX-ACCESS   read-write
        STATUS       current
        DESCRIPTION
            "To enable/disable the power back off (PBO) mechanism.
             set to 1 to enable, set to 2 to disable."
        ::= { vdslLinePrivateConfProfileEntry 22 }

    vdslLinePrivateConfProfileRateAdapt  OBJECT-TYPE
        SYNTAX       EnabledStatus
        MAX-ACCESS   read-write
        STATUS       current
        DESCRIPTION
            "To enable/disable the rate adaptive.
             set to 1 to enable, set to 2 to disable."
        ::= { vdslLinePrivateConfProfileEntry 23 }

    vdslLinePrivateConfProfileDsSnrMgn  OBJECT-TYPE
        SYNTAX       Integer32 (0..9)
        UNITS        "dB"
        MAX-ACCESS   read-write
        STATUS       current
        DESCRIPTION
            "The downstream signal to noise ratio margin,
            please note that the unit is in dB."
        ::= { vdslLinePrivateConfProfileEntry 24 }

    vdslLinePrivateConfProfileUsSnrMgn  OBJECT-TYPE
        SYNTAX       Integer32 (0..9)
        UNITS        "dB"
        MAX-ACCESS   read-write
        STATUS       current
        DESCRIPTION
            "The upstream signal to noise ratio margin,
            please note that the unit is in dB."
        ::= { vdslLinePrivateConfProfileEntry 25 }

    vdslLinePrivateConfProfileHamBandMask OBJECT-TYPE
        SYNTAX       BITS
            {
            amateurBand160m(0),   -- amateur radio band notch
            amateurBand80m(1),   -- amateur radio band notch
            amateurBand40m(2),   -- amateur radio band notch
            amateurBand30m(3)   -- amateur radio band notch
            }
        MAX-ACCESS   read-create
        STATUS       current
        DESCRIPTION
            "The transmit power spectral density mask code, used
            to avoid interference with HAM (Handheld Amateur Radio)
            radio bands by introducing power control (notching) in one
            or more of these bands.

            Amateur radio band notching is defined in the VDSL
            spectrum as follows:

            Band  Start Frequency     Stop Frequency
            ----  ------------------  --------------------------------
            30m   1810 kHz            2000 kHz
            40m   3500 kHz            3800 kHz (ETSI); 4000 kHz (ANSI)
            80m   7000 kHz            7100 kHz (ETSI); 7300 kHz (ANSI)
            160m  10100 kHz           10150 kHz

            Notching for each standard band can be enabled or disabled
            via the bit mask."
        REFERENCE    "DSLF TR-057, section 2.6"
        DEFVAL       { { } }
        ::= { vdslLinePrivateConfProfileEntry 26 }

    vdslLinePrivateConfProfileLineType OBJECT-TYPE
        SYNTAX       INTEGER
            {
            noChannel(1),         -- no channels exist
            fastOnly(2),          -- only fast channel exists
            interleavedOnly(3),   -- only interleaved channel exists
            fastOrInterleaved(4), -- either fast or interleaved channel
                                  -- exist, but only one at a time
            fastAndInterleaved(5) -- both fast and interleaved channels
                                  -- exist
            }
        MAX-ACCESS   read-create
        STATUS       current
        DESCRIPTION
            "This parameter provisions the VDSL physical entity at
            start-up by defining whether and how the line will be
            channelized, i.e. which channel type(s) are supported.
            If the line is to be channelized, the value will be other
            than noChannel(1).

            This configuration can be activated only during start-up.
            Afterwards, the value of vdslLineType coincides with the
            value of vdslLineConfLineType.  Depending on this vlaue,
            the corresponding entries in the ifTable for the
            interleaved and the fast channels are enabled or disabled
            according to the value of their ifOperStatus.

            Defined values are:

            noChannel(1)          -- no channels exist
            fastOnly(2)           -- only the fast channel exists
            interleavedOnly(3)    -- only the interleaved channel exists
            fastOrInterleaved(4)  -- either the fast or the interleaved
                                  -- channel exists, but only one at a
                                  -- time
            fastAndInterleaved(5) -- both fast and interleaved channels
                                  -- exist

            Note that 'slow' and 'interleaved' refer to the same
            channel."
        REFERENCE    "T1E1.4/2000-009R3, Part 1, common spec"
        DEFVAL       { noChannel }
        ::= { vdslLinePrivateConfProfileEntry 27 }

    vdslLinePrivateConfProfileRowStatus OBJECT-TYPE
        SYNTAX       RowStatus
        MAX-ACCESS   read-create
        STATUS       current
        DESCRIPTION
            "This object is used to create a new row or modify or
            delete an existing row in this table.

            A profile activated by setting this object to 'active'.
            When 'active' is set, the system will validate the profile.

            Before a profile can be deleted or taken out of
            service, (by setting this object to 'destroy' or
            'outOfService') it must be first unreferenced
            from all associated lines."
        ::= { vdslLinePrivateConfProfileEntry 28 }

    --
    -- Alarm configuration profile table
    --

    vdslLineAlarmConfProfileTable OBJECT-TYPE
        SYNTAX       SEQUENCE OF VdslLineAlarmConfProfileEntry
        MAX-ACCESS   not-accessible
        STATUS       current
        DESCRIPTION
            "This table contains information on the VDSL line alarm
            configuration.  One entry in this table reflects a profile
            defined by a manager which can be used to configure the
            VDSL line alarm thresholds."
        ::= { vdslLineMgt 20 }

    vdslLineAlarmConfProfileEntry OBJECT-TYPE
        SYNTAX       VdslLineAlarmConfProfileEntry
        MAX-ACCESS   not-accessible
        STATUS       current
        DESCRIPTION
            "Each entry consists of a list of parameters that
            represents the configuration of a VDSL line alarm
            profile.

            A default profile with an index of 'DEFVAL', will
            always exist and its parameters will be set to vendor
            specific values, unless otherwise specified in this
            document."
        INDEX { vdslLineAlarmConfProfileName }
        ::= { vdslLineAlarmConfProfileTable 1 }

    VdslLineAlarmConfProfileEntry ::=
        SEQUENCE
            {
            vdslLineAlarmConfProfileName       SnmpAdminString,
            vdslThresh15MinLofs                HCPerfIntervalThreshold,
            vdslThresh15MinLoss                HCPerfIntervalThreshold,
            vdslThresh15MinLprs                HCPerfIntervalThreshold,
            vdslThresh15MinLols                HCPerfIntervalThreshold,
            vdslThresh15MinESs                 HCPerfIntervalThreshold,
            vdslThresh15MinSESs                HCPerfIntervalThreshold,
            vdslThresh15MinUASs                HCPerfIntervalThreshold,
            vdslInitFailureNotifyEnable        TruthValue,
            vdslLineAlarmConfProfRowStatus     RowStatus
            }

    vdslLineAlarmConfProfileName OBJECT-TYPE
        SYNTAX       SnmpAdminString (SIZE (1..32))
        MAX-ACCESS   not-accessible
        STATUS       current
        DESCRIPTION
            "The name for this profile as specified by an
            adminstrator."
        ::= { vdslLineAlarmConfProfileEntry 1 }

    vdslThresh15MinLofs OBJECT-TYPE
        SYNTAX       HCPerfIntervalThreshold
        UNITS        "seconds"
        MAX-ACCESS   read-create
        STATUS       current
        DESCRIPTION
            "This object configures the threshold for the number of
             loss of frame seconds (lofs) within any given 15-minute
             performance data collection interval.  If the value of
             loss of frame seconds in a particular 15-minute collection
             interval reaches/exceeds this value, a
             vdslPerfLofsThreshNotification notification will be
             generated.  No more than one notification will be sent
             per interval."
        DEFVAL       { 0 }
        ::= { vdslLineAlarmConfProfileEntry 2 }

    vdslThresh15MinLoss OBJECT-TYPE
        SYNTAX       HCPerfIntervalThreshold
        UNITS        "seconds"
        MAX-ACCESS   read-create
        STATUS       current
        DESCRIPTION
            "This object configures the threshold for the number of
             loss of signal seconds (loss) within any given 15-minute
             performance data collection interval.  If the value of
             loss of signal seconds in a particular 15-minute
             collection interval reaches/exceeds this value, a
             vdslPerfLossThreshNotification notification will be
             generated.  One notification will be sent per interval
             per endpoint."
        DEFVAL       { 0 }
        ::= { vdslLineAlarmConfProfileEntry 3 }

    vdslThresh15MinLprs OBJECT-TYPE
        SYNTAX       HCPerfIntervalThreshold
        UNITS        "seconds"
        MAX-ACCESS   read-create
        STATUS       current
        DESCRIPTION
            "This object configures the threshold for the number of
             loss of power seconds (lprs) within any given 15-minute
             performance data collection interval.  If the value of
             loss of power seconds in a particular 15-minute collection
             interval reaches/exceeds this value, a
             vdslPerfLprsThreshNotification notification will be
             generated.  No more than one notification will be sent
             per interval."
        DEFVAL       { 0 }
        ::= { vdslLineAlarmConfProfileEntry 4 }

    vdslThresh15MinLols OBJECT-TYPE
        SYNTAX       HCPerfIntervalThreshold
        UNITS        "seconds"
        MAX-ACCESS   read-create
        STATUS       current
        DESCRIPTION
            "This object configures the threshold for the number of
             loss of link seconds (lols) within any given 15-minute
             performance data collection interval.  If the value of
             loss of power seconds in a particular 15-minute collection
             interval reaches/exceeds this value, a
             vdslPerfLolsThreshNotification notification will be
             generated.  No more than one notification will be sent
             per interval."
        DEFVAL       { 0 }
        ::= { vdslLineAlarmConfProfileEntry 5 }

    vdslThresh15MinESs OBJECT-TYPE
        SYNTAX       HCPerfIntervalThreshold
        UNITS        "seconds"
        MAX-ACCESS   read-create
        STATUS       current
        DESCRIPTION
            "This object configures the threshold for the number of
             errored seconds (ESs) within any given 15-minute
             performance data collection interval.  If the value of
             errored seconds in a particular 15-minute collection
             interval reaches/exceeds this value, a
             vdslPerfESsThreshNotification notification will be
             generated.  No more than one notification will be sent
             per interval."
        DEFVAL       { 0 }
        ::= { vdslLineAlarmConfProfileEntry 6 }

    vdslThresh15MinSESs OBJECT-TYPE
        SYNTAX       HCPerfIntervalThreshold
        UNITS        "seconds"
        MAX-ACCESS   read-create
        STATUS       current
        DESCRIPTION
            "This object configures the threshold for the number of
             severely errored seconds (SESs) within any given 15-minute
             performance data collection interval.  If the value of
             severely errored seconds in a particular 15-minute
             collection interval reaches/exceeds this value, a
             vdslPerfSESsThreshNotification notification will be
             generated.  No more than one notification will be sent
             per interval."
        DEFVAL       { 0 }
        ::= { vdslLineAlarmConfProfileEntry 7 }

    vdslThresh15MinUASs OBJECT-TYPE
        SYNTAX       HCPerfIntervalThreshold
        UNITS        "seconds"
        MAX-ACCESS   read-create
        STATUS       current
        DESCRIPTION
            "This object configures the threshold for the number of
             unavailable seconds (UASs) within any given 15-minute
             performance data collection interval.  If the value of
             unavailable seconds in a particular 15-minute collection
             interval reaches/exceeds this value, a
             vdslPerfUASsThreshNotification notification will be
             generated.  No more than one notification will be sent
             per interval."
        DEFVAL       { 0 }
        ::= { vdslLineAlarmConfProfileEntry 8 }

    vdslInitFailureNotifyEnable OBJECT-TYPE
        SYNTAX       TruthValue
        MAX-ACCESS   read-create
        STATUS       current
        DESCRIPTION
            "This object specifies if a vdslInitFailureNotification
            notification will be generated if an initialization
            failure occurs."
        DEFVAL       { false }
        ::= { vdslLineAlarmConfProfileEntry 9 }

    vdslLineAlarmConfProfRowStatus OBJECT-TYPE
        SYNTAX       RowStatus
        MAX-ACCESS   read-create
        STATUS       current
        DESCRIPTION
            "This object is used to create a new row or modify or
            delete an existing row in this table.

            A profile activated by setting this object to 'active'.
            When 'active' is set, the system will validate the profile.

            Before a profile can be deleted or taken out of service,
            (by setting this object to 'destroy' or 'outOfService') it
            must be first unreferenced from all associated lines."
        ::= { vdslLineAlarmConfProfileEntry 10 }

--
-- qosMgt
--

-- Management for Quality of Service (QoS) for network traffic.

--
-- rateLimitMgt
--

-- optional

rateLimitMgt        OBJECT IDENTIFIER ::= { qosMgt 1 }

rateLimitStatus OBJECT-TYPE
        SYNTAX      EnabledStatus
        MAX-ACCESS  read-write
        STATUS      current
        DESCRIPTION "Whether rate limit is enabled."
        ::= { rateLimitMgt 1 }

rateLimitPortTable OBJECT-TYPE
        SYNTAX      SEQUENCE OF RateLimitPortEntry
        MAX-ACCESS  not-accessible
        STATUS      current
        DESCRIPTION "Table for rate limit of each port."
        ::= { rateLimitMgt 2 }

rateLimitPortEntry OBJECT-TYPE
        SYNTAX      RateLimitPortEntry
        MAX-ACCESS  not-accessible
        STATUS      current
        DESCRIPTION "Entry for rate limit of each port."
        INDEX       { rlPortIndex }
        ::= { rateLimitPortTable 1 }

RateLimitPortEntry ::= SEQUENCE
{
    rlPortIndex              Integer32,
    rlPortInputLimit         Integer32,
    rlPortOutputLimit        Integer32,
    rlPortInputLimitPercent  Integer32,
    rlPortOutputLimitPercent Integer32,
    rlPortInputStatus        EnabledStatus,
    rlPortOutputStatus       EnabledStatus,
    rlPortInputLevel         Integer32,
    rlPortOutputLevel        Integer32,
    rlPortInputLimitInKilo   Integer32,
    rlPortOutputLimitInKilo  Integer32
}

rlPortIndex OBJECT-TYPE
        SYNTAX      Integer32
        MAX-ACCESS  not-accessible
        STATUS      current
        DESCRIPTION "The port and the trunk (including trunk member) interface of
                     the portTable. The interface identified by a particular value
                     of this index is the same interface as identified by the same
                     value of ifIndex in the IF-MIB."
        ::= { rateLimitPortEntry 1 }

-- non ACD
rlPortInputLimit OBJECT-TYPE
        SYNTAX      Integer32
        MAX-ACCESS  read-write
        STATUS      current
        DESCRIPTION "Value of the input rate limit. Its unit is megabits per
                     second. For a 100 Mbps port, the range is 1 to 100.
                     For a 1000 Mbps port, the range is 1 to 1000."
        ::= { rateLimitPortEntry 2 }

-- non ACD
rlPortOutputLimit OBJECT-TYPE
        SYNTAX      Integer32
        MAX-ACCESS  read-write
        STATUS      current
        DESCRIPTION "Value of the output rate limit. Its unit is megabits per
                     second. For a 100 Mbps port, the range is 1 to 100.
                     For a 1000 Mbps port, the range is 1 to 1000."
        ::= { rateLimitPortEntry 3 }

-- ACD
rlPortInputLimitPercent OBJECT-TYPE
        SYNTAX      Integer32
        MAX-ACCESS  read-write
        STATUS      current
        DESCRIPTION "Value of the input rate limit. Its unit is percent."
        ::= { rateLimitPortEntry 4 }
-- ACD
rlPortOutputLimitPercent OBJECT-TYPE
        SYNTAX      Integer32
        MAX-ACCESS  read-write
        STATUS      current
        DESCRIPTION "Value of the output rate limit. Its unit is percent."
        ::= { rateLimitPortEntry 5 }

-- all need (both acd and non-acd)
rlPortInputStatus OBJECT-TYPE
        SYNTAX      EnabledStatus
        MAX-ACCESS  read-write
        STATUS      current
        DESCRIPTION "Whether input rate limit is enabled for this port."
        ::= { rateLimitPortEntry 6 }

-- all need (both acd and non-acd)
rlPortOutputStatus OBJECT-TYPE
        SYNTAX      EnabledStatus
        MAX-ACCESS  read-write
        STATUS      current
        DESCRIPTION "Whether output rate limit is enabled for this port."
        ::= { rateLimitPortEntry 7 }

--same as rlPortInputLimit, special for LEO_X 's chip
rlPortInputLevel OBJECT-TYPE
        SYNTAX      Integer32(1..30)
        MAX-ACCESS  read-write
        STATUS      current
        DESCRIPTION "The Level of the input rate limit."
        ::= { rateLimitPortEntry 8 }

--same as rlPortOutputLimit, special for LEO_X 's chip
rlPortOutputLevel OBJECT-TYPE
        SYNTAX      Integer32(1..30)
        MAX-ACCESS  read-write
        STATUS      current
        DESCRIPTION "The Level of the output rate limit."
        ::= { rateLimitPortEntry 9 }

--ES3528M-FLF-38-00015
rlPortInputLimitInKilo OBJECT-TYPE
        SYNTAX      Integer32
        MAX-ACCESS  read-write
        STATUS      current
        DESCRIPTION "Value of the input rate limit. Its unit is kilobits per
                     second. For a 100 Mbps port, the range is 64 to 100000.
                     For a 1000 Mbps port, the range is 64 to 1000000.
                     For a 10 Gbps port, the range is 64 to 10000000."
        ::= { rateLimitPortEntry 10 }

rlPortOutputLimitInKilo OBJECT-TYPE
        SYNTAX      Integer32
        MAX-ACCESS  read-write
        STATUS      current
        DESCRIPTION "Value of the output rate limit. Its unit is kilobits per
                     second. For a 100 Mbps port, the range is 64 to 100000.
                     For a 1000 Mbps port, the range is 64 to 1000000.
                     For a 10 Gbps port, the range is 64 to 10000000."
        ::= { rateLimitPortEntry 11 }



rateLimitGigaGranularity OBJECT-TYPE
        SYNTAX      Integer32
        MAX-ACCESS  read-write
        STATUS      current
        DESCRIPTION "The rate limit gigabit ethernet granularity."
        ::= { rateLimitMgt 3 }


rateLimitFastEthernetGranularity OBJECT-TYPE
        SYNTAX      Integer32
        MAX-ACCESS  read-write
        STATUS      current
        DESCRIPTION "The rate limit fast ethernet granularity."
        ::= { rateLimitMgt 4 }

rateLimitCosPrioTable OBJECT-TYPE
        SYNTAX      SEQUENCE OF RateLimitCosPrioEntry
        MAX-ACCESS  not-accessible
        STATUS      current
        DESCRIPTION "Table for the rate limit, per port, per Class of Service priority."
        ::= { rateLimitMgt 5 }

rateLimitCosPrioEntry OBJECT-TYPE
        SYNTAX      RateLimitCosPrioEntry
        MAX-ACCESS  not-accessible
        STATUS      current
        DESCRIPTION "Entry for the rate limit, per port, per Class of Service priority."
        INDEX       { rateLimitCosPrioIfIndex, rateLimitCosPrioValue}
        ::= { rateLimitCosPrioTable 1 }

RateLimitCosPrioEntry ::= SEQUENCE
{
    rateLimitCosPrioIfIndex         InterfaceIndex,
    rateLimitCosPrioValue           Unsigned32,
    rateLimitCosPrioRateLimitValue  Unsigned32
}

rateLimitCosPrioIfIndex OBJECT-TYPE
        SYNTAX      InterfaceIndex
        MAX-ACCESS  not-accessible
        STATUS      current
        DESCRIPTION "The port that the rate limit function is performed."
        ::= { rateLimitCosPrioEntry 1 }

rateLimitCosPrioValue OBJECT-TYPE
        SYNTAX      Unsigned32
        MAX-ACCESS  not-accessible
        STATUS      current
        DESCRIPTION "The Class of Service priority value."
        ::= { rateLimitCosPrioEntry 2 }

rateLimitCosPrioRateLimitValue OBJECT-TYPE
        SYNTAX      Unsigned32
        MAX-ACCESS  read-write
        STATUS      current
        DESCRIPTION "The rate limit value of the Class of Service priority. If the
                     value equals 0, it means that the rate limit function
                     is disabled."
        ::= { rateLimitCosPrioEntry 3 }


--
--markerMgt
--
markerMgt        OBJECT IDENTIFIER ::= { qosMgt 2 }

markerTable OBJECT-TYPE
        SYNTAX      SEQUENCE OF MarkerEntry
        MAX-ACCESS  not-accessible
        STATUS      current
        DESCRIPTION "The marker table."
        ::= { markerMgt 1 }

markerEntry OBJECT-TYPE
        SYNTAX      MarkerEntry
        MAX-ACCESS  not-accessible
        STATUS      current
        DESCRIPTION "Entry for marker table."
        INDEX       { markerIfIndex,markerAclName }
        ::= { markerTable 1 }

MarkerEntry ::= SEQUENCE
{
    markerIfIndex             Integer32,
    markerAclName             DisplayString,
    markerActionBitList       BITS,
    markerDscp                Integer32,
    markerPrecedence          Integer32,
    markerPriority            Integer32,
    markerStatus              RowStatus
}

markerIfIndex OBJECT-TYPE
        SYNTAX      Integer32
        MAX-ACCESS  not-accessible
        STATUS      current
        DESCRIPTION "The interface index of the marker table.
                    The interface identified by a particular value
                     of this index is the same interface as identified by the same
                     value of ifIndex in the IF-MIB."
        ::= { markerEntry 1 }

markerAclName OBJECT-TYPE
        SYNTAX      DisplayString (SIZE(1..16))
        MAX-ACCESS  not-accessible
        STATUS      current
        DESCRIPTION "The name of an ACL. Within a feature a unique
                    name is used to identify the list to which
                    the entry belongs in the device."
        ::= { markerEntry 2 }

markerActionBitList OBJECT-TYPE
        SYNTAX      BITS
                    {
                        dscp(0),
                        precedence(1),
                        priority(2)
                    }
        MAX-ACCESS  read-create
        STATUS      current
        DESCRIPTION "The marker action bit list,
                     according to the position of the BITS syntax.
                     for example:
                     bit 0 + bit 1 means dscp(0) and precedence(1)
                     bit 2 means priority(2)."
        ::= { markerEntry 3 }

markerDscp OBJECT-TYPE
        SYNTAX       Integer32(0..63)
        MAX-ACCESS  read-create
        STATUS      current
        DESCRIPTION "The DSCP value of the marker entry."
        ::= { markerEntry 4 }

markerPrecedence OBJECT-TYPE
        SYNTAX       Integer32(0..7)
        MAX-ACCESS  read-create
        STATUS      current
        DESCRIPTION "The precedence value of the marker entry."
        ::= { markerEntry 5 }

markerPriority OBJECT-TYPE
        SYNTAX       Integer32(0..7)
        MAX-ACCESS  read-create
        STATUS      current
        DESCRIPTION "The priority value of the marker entry."
        ::= { markerEntry 6 }

markerStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { markerEntry 7 }

cosMgt        OBJECT IDENTIFIER ::= { qosMgt 3 }

--prioAclToCosMappingTable
prioAclToCosMappingTable OBJECT-TYPE
        SYNTAX      SEQUENCE OF PrioAclToCosMappingEntry
        MAX-ACCESS  not-accessible
        STATUS      current
        DESCRIPTION "Table for ACL to CoS Mapping."
        ::= { cosMgt 1 }

prioAclToCosMappingEntry OBJECT-TYPE
        SYNTAX      PrioAclToCosMappingEntry
        MAX-ACCESS  not-accessible
        STATUS      current
        DESCRIPTION "Entry for ACL to CoS Mapping."
        INDEX       { prioAclToCosMappingIfIndex, prioAclToCosMappingAclName }
        ::= { prioAclToCosMappingTable 1 }

PrioAclToCosMappingEntry ::= SEQUENCE
{
    prioAclToCosMappingIfIndex    Integer32,
    prioAclToCosMappingAclName  DisplayString,
    prioAclToCosMappingCosValue      Integer32,
    prioAclToCosMappingStatus      RowStatus
}

prioAclToCosMappingIfIndex OBJECT-TYPE
        SYNTAX      Integer32
        MAX-ACCESS  not-accessible
        STATUS      current
        DESCRIPTION "The port interface of the prioAclToCosMappingEntry. The interface
                     identified by a particular value of this index is the
                     same interface as identified by the same value of
                     ifIndex in the IF-MIB."
        ::= { prioAclToCosMappingEntry 1 }

prioAclToCosMappingAclName OBJECT-TYPE
        SYNTAX      DisplayString (SIZE(1..16))
        MAX-ACCESS  not-accessible
        STATUS      current
        DESCRIPTION "The name of an IP ACL. Within a feature a unique name is
                     used to identify the list to which the entry belongs
                     in the device."
        ::= { prioAclToCosMappingEntry 2 }

prioAclToCosMappingCosValue OBJECT-TYPE
        SYNTAX      Integer32 (0..7)
        MAX-ACCESS  read-create
        STATUS      current
        DESCRIPTION "CoS value of the prioAclToCosMappingTable."
        ::= { prioAclToCosMappingEntry 3 }

prioAclToCosMappingStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { prioAclToCosMappingEntry 4 }

--cosQueueMgt
cosQueueMgt OBJECT-TYPE
        SYNTAX      NULL
        MAX-ACCESS  not-accessible
        STATUS      current
        DESCRIPTION ""
        ::= { cosMgt 2 }

cosQueueStartUpLimit OBJECT-TYPE
        SYNTAX      OCTET STRING
        MAX-ACCESS  read-write
        STATUS      current
        DESCRIPTION "The cos queue range of the value of each queue is from 1
                     to 9 and the sum of 8 queues is equal to 16.This is
                     because totally 8192 packets that ASIC provides for the
                     8 queues, and the unit is 512 packets, so 8192/512 = 16.
                     When it set the value,it will check the sum of the 8 cos
                     queue is equal to 16,if not, just return error message.
                     The value saves in database ,not write into switch chip.
                     Format part:
                                From begin to end ,queue 0 is mapping to first
                                byte,queue 1 is mapping to second byte,and so on.
                     Warning:This will take effect only after saving the
                             configuration and rebooting the switch."
        ::= { cosQueueMgt 1 }

cosQueueOperatingLimit OBJECT-TYPE
        SYNTAX      OCTET STRING
        MAX-ACCESS  read-only
        STATUS      current
        DESCRIPTION "Show cos queue running state information."
        ::= { cosQueueMgt 2 }

--
--diffServMgt
--

diffServMgt        OBJECT IDENTIFIER ::= { qosMgt 4 }

--diffServClfrExtTable
diffServClfrExtTable OBJECT-TYPE
    SYNTAX          SEQUENCE OF DiffServClfrExtEntry
    MAX-ACCESS      not-accessible
    STATUS          current
    DESCRIPTION     "The conceptual table of diffServClfrExtEntry."
    REFERENCE       "DIFFSERV-MIB.diffServClfrTable"
    ::= { diffServMgt 1 }

diffServClfrExtEntry OBJECT-TYPE
    SYNTAX          DiffServClfrExtEntry
    MAX-ACCESS      not-accessible
    STATUS          current
    DESCRIPTION     "The conceptual row for diffServClfrExtTable."
    AUGMENTS        {diffServClfrEntry}
    ::= { diffServClfrExtTable 1 }

DiffServClfrExtEntry ::= SEQUENCE
    {
        diffServClfrExtName                  DisplayString,
        diffServClfrExtDesc                  DisplayString
    }

diffServClfrExtName OBJECT-TYPE
    SYNTAX          DisplayString(SIZE (0..16))
    MAX-ACCESS      read-write
    STATUS          current
    DESCRIPTION     "The policy-map name."
    ::= { diffServClfrExtEntry 1 }

diffServClfrExtDesc OBJECT-TYPE
    SYNTAX          DisplayString(SIZE (0..64))
    MAX-ACCESS      read-write
    STATUS          current
    DESCRIPTION     "The description of policy-map."
    ::= { diffServClfrExtEntry 2 }

--diffServClassMapNextFree
diffServClassMapNextFree OBJECT-TYPE
    SYNTAX          IndexIntegerNextFree
    MAX-ACCESS      read-only
    STATUS          current
    DESCRIPTION     "This object contains an unused value for diffServClassMapId,
                     or a zero to indicate that none exist."
    ::= { diffServMgt 2 }


--diffServClassMapTable

diffServClassMapTableOld    OBJECT-TYPE -- Duplicate definition diffServClassMapTable
    SYNTAX          SEQUENCE OF DiffServClassMapEntryOld -- Duplicate definition DiffServClassMapEntry
    MAX-ACCESS      not-accessible
    STATUS          current
    DESCRIPTION     "The conceptual table of diffServClassMapEntry."
    ::= { diffServMgt 3 }

diffServClassMapEntryOld OBJECT-TYPE -- Duplicate definition diffServClassMapEntry
    SYNTAX          DiffServClassMapEntryOld -- Duplicate definition DiffServClassMapEntry
    MAX-ACCESS      not-accessible
    STATUS          current
    DESCRIPTION     "The conceptual row for diffServClassMapTable."
    INDEX           {diffServClassMapId}
    ::= { diffServClassMapTableOld 1 } -- Duplicate definition diffServClassMapTable

DiffServClassMapEntryOld ::= SEQUENCE  -- Duplicate definition DiffServClassMapEntry
    {
        diffServClassMapId                  IndexInteger,
        diffServClassMapNameOld                DisplayString, -- Duplicate definition diffServClassMapName
        diffServClassMapDesc                DisplayString,
        diffServClassMapType                INTEGER,
        diffServCalssMapStatus              RowStatus,
        diffServClassMapMatchDscp           Unsigned32,
        diffServClassMapMatchPriority       Unsigned32
    }

diffServClassMapId OBJECT-TYPE
    SYNTAX          IndexInteger
    MAX-ACCESS      not-accessible
    STATUS          current
    DESCRIPTION     "An index that enumerates the Class Map entries.
                     Managers obtain new values for row creation in this table
                     by reading diffServClassMapNextFree."
    ::= { diffServClassMapEntryOld 1 } -- Duplicate definition DiffServClassMapEntry

diffServClassMapNameOld OBJECT-TYPE -- Duplicate definition diffServClassMapName
    SYNTAX          DisplayString(SIZE (0..16))
    MAX-ACCESS      read-create
    STATUS          current
    DESCRIPTION     "The class-map name."
    ::= { diffServClassMapEntryOld 2 } -- Duplicate definition DiffServClassMapEntry


diffServClassMapDesc OBJECT-TYPE
    SYNTAX          DisplayString(SIZE (0..64))
    MAX-ACCESS      read-create
    STATUS          current
    DESCRIPTION     "The description of class-map."
    ::= { diffServClassMapEntryOld 3 } -- Duplicate definition DiffServClassMapEntry

diffServClassMapType OBJECT-TYPE
    SYNTAX          INTEGER {
                             matchAll (1),
                             matchAny (2)
                            }
    MAX-ACCESS      read-create
    STATUS          current
    DESCRIPTION     "The class-map type."
    ::= { diffServClassMapEntryOld 4 } -- Duplicate definition DiffServClassMapEntry

diffServCalssMapStatus OBJECT-TYPE
    SYNTAX          RowStatus
    MAX-ACCESS      read-create
    STATUS          current
    DESCRIPTION     "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { diffServClassMapEntryOld 5 } -- Duplicate definition DiffServClassMapEntry

diffServClassMapMatchDscp OBJECT-TYPE
    SYNTAX          Unsigned32(0..64)
    MAX-ACCESS      read-create
    STATUS          current
    DESCRIPTION
        "The value that the DSCP in the packet must match this entry.
         The value of 64 indicates that a specific DSCP value has not been defined."
    ::= { diffServClassMapEntryOld 6 }

diffServClassMapMatchPriority OBJECT-TYPE
    SYNTAX          Unsigned32(0..8)
    MAX-ACCESS      read-create
    STATUS          current
    DESCRIPTION
        "The value that the Priority in the frame must match this entry.
         The value of 8 indicates that a specific Priority value has not been defined."
    ::= { diffServClassMapEntryOld 7 }

--diffServClassMapElementNextFree
diffServClassMapElementNextFree OBJECT-TYPE
    SYNTAX          IndexIntegerNextFree
    MAX-ACCESS      read-only
    STATUS          current
    DESCRIPTION     "This object contains an unused value for diffServClassMapElementId,
                     or a zero to indicate that none exist."
    ::= { diffServMgt 4 }

--diffServClassMapElementTable
diffServClassMapElementTable OBJECT-TYPE
    SYNTAX          SEQUENCE OF DiffServClassMapElementEntry
    MAX-ACCESS      not-accessible
    STATUS          current
    DESCRIPTION     "The conceptual table of diffServClassMapElementEntry."
    ::= { diffServMgt 5 }

diffServClassMapElementEntry OBJECT-TYPE
    SYNTAX          DiffServClassMapElementEntry
    MAX-ACCESS      not-accessible
    STATUS          current
    DESCRIPTION     "The conceptual row for diffServClassMapElementTable."
    INDEX           {diffServClassMapId, diffServClassMapElementId}
    ::= { diffServClassMapElementTable 1 }

DiffServClassMapElementEntry ::= SEQUENCE
    {
        diffServClassMapElementId                  IndexInteger,
        diffServClassMapElementSpecific            RowPointer,
        diffServClassMapElementStatus              RowStatus
    }

diffServClassMapElementId OBJECT-TYPE
    SYNTAX          IndexInteger
    MAX-ACCESS      not-accessible
    STATUS          current
    DESCRIPTION     "An index that enumerates the Class Map Element entries.
                     Managers obtain new values for row creation in this table by
                     reading diffServClfrElementNextFree."
    ::= { diffServClassMapElementEntry 1 }

diffServClassMapElementSpecific OBJECT-TYPE
    SYNTAX          RowPointer
    MAX-ACCESS      read-create
    STATUS          current
    DESCRIPTION     "A pointer to a valid entry in another table, filter table,
                     that describes the applicable classification parameters.

                     This RowPointer should point to an instance of one of:
                     diffServMultiFieldClfrEntry, diffServMultiFieldClfrExtEntry,
                     aclIpEntry, aclMacEntry."
    ::= { diffServClassMapElementEntry 2 }

diffServClassMapElementStatus OBJECT-TYPE
    SYNTAX          RowStatus
    MAX-ACCESS      read-create
    STATUS          current
    DESCRIPTION     "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { diffServClassMapElementEntry 3 }


--diffServMultiFieldClfrExtTable

diffServMultiFieldClfrExtTable OBJECT-TYPE
    SYNTAX          SEQUENCE OF DiffServMultiFieldClfrExtEntry
    MAX-ACCESS      not-accessible
    STATUS          current
    DESCRIPTION     "The conceptual table of diffServMultiFieldClfrExtEntry."
    REFERENCE       "DIFFSERV-MIB.diffServMultiFieldClfrTable"
    ::= { diffServMgt 6 }

diffServMultiFieldClfrExtEntry OBJECT-TYPE
    SYNTAX          DiffServMultiFieldClfrExtEntry
    MAX-ACCESS      not-accessible
    STATUS          current
    DESCRIPTION     "The conceptual row for diffServMultiFieldClfrExtTable."
    AUGMENTS        {diffServMultiFieldClfrEntry}
    ::= { diffServMultiFieldClfrExtTable 1 }

DiffServMultiFieldClfrExtEntry ::= SEQUENCE
    {
        diffServMultiFieldClfrExtType              BITS,
        diffServMultiFieldClfrExtVid               VlanIndex,
        diffServMultiFieldClfrExtIpPrecedence      Integer32,
        diffServMultiFieldClfrExtClassType         INTEGER,
        diffServMultiFieldClfrExtEtherType         Integer32
    }

--non 3com only start
diffServMultiFieldClfrExtType OBJECT-TYPE
    SYNTAX          BITS
                    {
                            dscp(0),
                            ipPrecedence(1),
                            vid(2)
                    }
    MAX-ACCESS      read-write
    STATUS          current
    DESCRIPTION     "Indicates the current type of the multi filed entry. This is a
                    bit-map of possible conditions. The various bit
                    positions are:

                    0: dscp.
                    1: ipPrecedence.
                    2: vid

                    bit 0(dscp) refer to object DIFFSERV-MIB.diffServMultiFieldClfrEntry.diffServMultiFieldClfrDscp.
                    bit 1(ipPrecedence) refer to object DIFFSERV-MIB.diffServMultiFieldClfrEntry.diffServMultiFieldClfrFlowId.
                    bit 2(vid) refer to object PRIVATE-MIB.diffServMultiFieldClfrExtEntry.diffServMultiFieldClfrExtVid."
    ::= { diffServMultiFieldClfrExtEntry 1 }

diffServMultiFieldClfrExtVid OBJECT-TYPE
    SYNTAX          VlanIndex
    MAX-ACCESS      read-write
    STATUS          current
    DESCRIPTION     "The VLAN ID to match against the packet's VLAN ID."
    REFERENCE  "P-BRIDGE-MIB.VlanIndex."
    ::= { diffServMultiFieldClfrExtEntry 2 }

diffServMultiFieldClfrExtIpPrecedence OBJECT-TYPE
    SYNTAX          Integer32 (0..7)
    MAX-ACCESS      read-write
    STATUS          current
    DESCRIPTION     "The IP precedence value to match against the packet's IP precedence value."
    ::= { diffServMultiFieldClfrExtEntry 3 }
--non 3com only end

--3com only start
diffServMultiFieldClfrExtClassType  OBJECT-TYPE
    SYNTAX          INTEGER
                    {
                        srcAddr(1),
                        dstAddr(2),
                        bothAddr(3),
                        protocol(4),
                        srcL4Port(5),
                        dstL4Port(6),
                        bothL4Port(7),
                        dscp(8),
                        etherType(9)
                    }
    MAX-ACCESS      read-write
    STATUS          current
    DESCRIPTION     "Indicates the current type of the multi filed entry.
                     for example, srcAddr(1) means only
                     the following objects in diffServMultiFieldClfrTable are meaningful,
                     and the other fields can be ignored(except diffServMultiFieldClfrStorage and diffServMultiFieldClfrStatus):

                         diffServMultiFieldClfrSrcAddr(5)
                         diffServMultiFieldClfrSrcPrefixLength(6)

                     For all possible ClassType, please see as below:
                     srcAddr(1):   DIFFSERV-MIB.diffServMultiFieldClfrEntry.diffServMultiFieldClfrSrcAddr(5)
                                   DIFFSERV-MIB.diffServMultiFieldClfrEntry.diffServMultiFieldClfrSrcPrefixLength(6)

                     dstAddr(2):   DIFFSERV-MIB.diffServMultiFieldClfrEntry.diffServMultiFieldClfrDstAddr(3)
                                   DIFFSERV-MIB.diffServMultiFieldClfrEntry.diffServMultiFieldClfrDstPrefixLength(4)

                     bothAddr(3):  DIFFSERV-MIB.diffServMultiFieldClfrEntry.diffServMultiFieldClfrDstAddr(3)
                                   DIFFSERV-MIB.diffServMultiFieldClfrEntry.diffServMultiFieldClfrDstPrefixLength(4)
                                   DIFFSERV-MIB.diffServMultiFieldClfrEntry.diffServMultiFieldClfrSrcAddr(5)
                                   DIFFSERV-MIB.diffServMultiFieldClfrEntry.diffServMultiFieldClfrSrcPrefixLength(6)

                     protocol(4):  DIFFSERV-MIB.diffServMultiFieldClfrEntry.diffServMultiFieldClfrProtocol(9)

                     srcL4Port(5): DIFFSERV-MIB.diffServMultiFieldClfrEntry.diffServMultiFieldClfrSrcL4PortMin(12)
                                   DIFFSERV-MIB.diffServMultiFieldClfrEntry.diffServMultiFieldClfrSrcL4PortMax(13)

                     dstL4Port(6): DIFFSERV-MIB.diffServMultiFieldClfrEntry.diffServMultiFieldClfrDstL4PortMin(10)
                                   DIFFSERV-MIB.diffServMultiFieldClfrEntry.diffServMultiFieldClfrDstL4PortMax(11)

                     bothL4Port(7):DIFFSERV-MIB.diffServMultiFieldClfrEntry.diffServMultiFieldClfrDstL4PortMin(10)
                                   DIFFSERV-MIB.diffServMultiFieldClfrEntry.diffServMultiFieldClfrDstL4PortMax(11)
                                   DIFFSERV-MIB.diffServMultiFieldClfrEntry.diffServMultiFieldClfrSrcL4PortMin(12)
                                   DIFFSERV-MIB.diffServMultiFieldClfrEntry.diffServMultiFieldClfrSrcL4PortMax(13)

                     dscp(8):      DIFFSERV-MIB.diffServMultiFieldClfrEntry.diffServMultiFieldClfrDscp(7)

                     etherType(9): PRIVATE-MIB.diffServMultiFieldClfrExtEntry.diffServMultiFieldClfrExtEtherType(5)"
    ::= { diffServMultiFieldClfrExtEntry 4 }

diffServMultiFieldClfrExtEtherType  OBJECT-TYPE
    SYNTAX          Integer32 (1536..65535)
    MAX-ACCESS      read-write
    STATUS          current
    DESCRIPTION     "The ether type value."
    ::= { diffServMultiFieldClfrExtEntry 5 }
--3com only end

--diffServToSMarkActTable
diffServToSMarkActTable  OBJECT-TYPE
    SYNTAX          SEQUENCE OF DiffServToSMarkActEntry
    MAX-ACCESS      not-accessible
    STATUS          current
    DESCRIPTION     "The conceptual table of diffServToSMarkActEntry."
    ::= { diffServMgt 7 }

diffServToSMarkActEntry OBJECT-TYPE
    SYNTAX          DiffServToSMarkActEntry
    MAX-ACCESS      not-accessible
    STATUS          current
    DESCRIPTION     "The conceptual row for diffServToSMarkActTable."
    INDEX           { diffServToSMarkActToS }
    ::= { diffServToSMarkActTable 1 }

DiffServToSMarkActEntry ::= SEQUENCE
    {
        diffServToSMarkActToS              Integer32
    }

diffServToSMarkActToS OBJECT-TYPE
    SYNTAX          Integer32 (0..32)
    MAX-ACCESS      read-only
    STATUS          current
    DESCRIPTION     "The ToS value referenced by a diffServActionSpecific attribute."
    ::= { diffServToSMarkActEntry 1 }

--diffServDot1pMarkActTable
diffServDot1pMarkActTable OBJECT-TYPE
    SYNTAX          SEQUENCE OF DiffServDot1pMarkActEntry
    MAX-ACCESS      not-accessible
    STATUS          current
    DESCRIPTION     "The conceptual table of diffServDot1pMarkActEntry."
    ::= { diffServMgt 8 }

diffServDot1pMarkActEntry OBJECT-TYPE
    SYNTAX          DiffServDot1pMarkActEntry
    MAX-ACCESS      not-accessible
    STATUS          current
    DESCRIPTION     "The conceptual row for diffServDot1pMarkActTable."
    INDEX           { diffServDot1pMarkActDot1p }
    ::= { diffServDot1pMarkActTable 1 }

DiffServDot1pMarkActEntry ::= SEQUENCE
    {
        diffServDot1pMarkActDot1p              Integer32
    }

diffServDot1pMarkActDot1p OBJECT-TYPE
    SYNTAX          Integer32 (0..7)
    MAX-ACCESS      read-only
    STATUS          current
    DESCRIPTION     "The Dot1p value referenced by a diffServActionSpecific attribute."
    ::= { diffServDot1pMarkActEntry 1 }


diffServPortTable OBJECT-TYPE
        SYNTAX      SEQUENCE OF DiffServPortEntry
        MAX-ACCESS  not-accessible
        STATUS      current
        DESCRIPTION "Table for difference service of each port."
        ::= { diffServMgt 9 }

diffServPortEntry OBJECT-TYPE
        SYNTAX      DiffServPortEntry
        MAX-ACCESS  not-accessible
        STATUS      current
        DESCRIPTION "Entry for difference service of each port."
        INDEX       { diffServPortIfIndex }
        ::= { diffServPortTable 1 }

DiffServPortEntry ::= SEQUENCE
{
    diffServPortIfIndex             Integer32,
    diffServPortPolicyMapIndex      Integer32,
    diffServPortIngressIpAclIndex   Integer32,
    diffServPortIngressMacAclIndex  Integer32,
    diffServPortIngressIpv6AclIndex Integer32
}

diffServPortIfIndex OBJECT-TYPE
        SYNTAX      Integer32
        MAX-ACCESS  not-accessible
        STATUS      current
        DESCRIPTION "This object is the interface index of diffServPortEntry.
                     The interface identified by a particular value of this
                     index is the same interface as identified by the same
                     value of ifIndex in the IF-MIB."
        ::= { diffServPortEntry 1 }

diffServPortPolicyMapIndex OBJECT-TYPE
    SYNTAX      Integer32
    MAX-ACCESS  read-write
    STATUS      current
    DESCRIPTION "Specifies the policy map binding to the interface.
                 The policy map identified by a particular value of
                 this index is associated with the same DiffServPolicyMapEntry
                 as identified by the same value of diffServPolicyMapIndex."
    ::= { diffServPortEntry 2 }

diffServPortIngressIpAclIndex OBJECT-TYPE
    SYNTAX      Integer32
    MAX-ACCESS  read-write
    STATUS      current
    DESCRIPTION "Specifies the ingress IP ACL binding to the interface.The
                 ingress IP ACL identified by a particular value of this
                 index is associated with the same diffServAclEntry as
                 identified by the same value of diffServAclIndex."
    ::= { diffServPortEntry 3 }

diffServPortIngressMacAclIndex OBJECT-TYPE
    SYNTAX      Integer32
    MAX-ACCESS  read-write
    STATUS      current
    DESCRIPTION "Specifies the ingress Mac ACL binding to the interface.The
                 ingress Mac ACL identified by a particular value of this
                 index is associated with the same diffServAclEntry as
                 identified by the same value of diffServAclIndex."
    ::= { diffServPortEntry 4 }

diffServPortIngressIpv6AclIndex OBJECT-TYPE
    SYNTAX      Integer32
    MAX-ACCESS  read-write
    STATUS      current
    DESCRIPTION "Specifies the ingress Ipv6 ACL binding to the interface.The
                 ingress Ipv6 ACL identified by a particular value of this
                 index is associated with the same diffServAclEntry as
                 identified by the same value of diffServAclIndex."
    ::= { diffServPortEntry 5 }

diffServPolicyMapTable OBJECT-TYPE
        SYNTAX      SEQUENCE OF DiffServPolicyMapEntry
        MAX-ACCESS  not-accessible
        STATUS      current
        DESCRIPTION "Table for policy map."
        ::= { diffServMgt 10 }

diffServPolicyMapEntry OBJECT-TYPE
        SYNTAX      DiffServPolicyMapEntry
        MAX-ACCESS  not-accessible
        STATUS      current
        DESCRIPTION "Entry for policy map."
        INDEX       { diffServPolicyMapIndex }
        ::= { diffServPolicyMapTable 1 }

DiffServPolicyMapEntry ::= SEQUENCE
{
    diffServPolicyMapIndex              Integer32,
    diffServPolicyMapName               DisplayString,
    diffServPolicyMapDescription        DisplayString,
    diffServPolicyMapElementIndexList   OCTET STRING,
    diffServPolicyMapStatus             RowStatus
}

diffServPolicyMapIndex OBJECT-TYPE
        SYNTAX      Integer32
        MAX-ACCESS  not-accessible
        STATUS      current
        DESCRIPTION "An index that uniquely identifies an entry in this
                     table."
        ::= { diffServPolicyMapEntry 1 }

diffServPolicyMapName OBJECT-TYPE
    SYNTAX      DisplayString (SIZE (1..16))
    MAX-ACCESS  read-create
    STATUS      current
    DESCRIPTION "The name of this entry."
    ::= { diffServPolicyMapEntry 2 }

diffServPolicyMapDescription OBJECT-TYPE
    SYNTAX      DisplayString (SIZE (0..64))
    MAX-ACCESS  read-create
    STATUS      current
    DESCRIPTION "The description of this entry."
    ::= { diffServPolicyMapEntry 3 }

diffServPolicyMapElementIndexList OBJECT-TYPE
    SYNTAX      OCTET STRING (SIZE (0..32))
    MAX-ACCESS  read-only
    STATUS      current
    DESCRIPTION "The octet string containes the diffServPolicyMapElementEntry
                 indexes. One octet expresses one index .This indexes list
                 indicates the diffServPolicyMapEntrys which are belong to
                 this entry."
    ::= { diffServPolicyMapEntry 4 }

diffServPolicyMapStatus OBJECT-TYPE
    SYNTAX      RowStatus
    MAX-ACCESS  read-create
    STATUS      current
    DESCRIPTION "This object is used to create a new row or modify or delete
                 an existing row in this table.The status column has six
                 defined values:
                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServPolicyMapEntry 5 }


diffServPolicyMapAttachCtl  OBJECT IDENTIFIER   ::= { diffServMgt 11 }

diffServPolicyMapAttachCtlIndex OBJECT-TYPE
        SYNTAX      Integer32
        MAX-ACCESS  read-write
        STATUS      current
        DESCRIPTION "Specifies the policy map as the target to relate with
                     the policy map element. The policy map identified by
                     a particular value of this index is associated with
                     the same diffservPolicyMapEntry as identified by the
                     same value of diffservPolicyMapIndex."
        ::= { diffServPolicyMapAttachCtl 1 }

diffServPolicyMapAttachCtlElementIndex OBJECT-TYPE
    SYNTAX      Integer32
    MAX-ACCESS  read-write
    STATUS      current
    DESCRIPTION "Specifies the policy map element to relate with the policy
                 map. The policy map element identified by a particular value
                 of this index is associated with the same
                 diffservPolicyMapElmentEntry as identified by the same
                 value of diffservPolicyMapElmentIndex."
    ::= { diffServPolicyMapAttachCtl 2 }

diffServPolicyMapAttachCtlAction OBJECT-TYPE
    SYNTAX      INTEGER
                    {
                        notAction(1),
                        attaching(2),
                        notAttaching(3)
                    }
    MAX-ACCESS  read-write
    STATUS      current
    DESCRIPTION "When setting this object to attach(2) to begin the attaching
                 operation, a particular policy map element is attached to a
                 particular policy map. When setting this object to
                 notAttach(3) to begin the not attaching operation, a
                 particular policy map element is not attached to a particular
                 policy map. When action finsh or no action, the value of this
                 object is noAction(1). A particular policy map is
                 specified in the diffServPolicyMapAttachCtlIndex.A
                 particularpolicy map element is specified in the
                 diffServPolicyMapAttachCtlElementIndex."
    ::= { diffServPolicyMapAttachCtl 3 }


diffServPolicyMapElementTable OBJECT-TYPE
        SYNTAX      SEQUENCE OF DiffServPolicyMapElementEntry
        MAX-ACCESS  not-accessible
        STATUS      current
        DESCRIPTION "Table for policy map element."
        ::= { diffServMgt 12 }

diffServPolicyMapElementEntry OBJECT-TYPE
        SYNTAX      DiffServPolicyMapElementEntry
        MAX-ACCESS  not-accessible
        STATUS      current
        DESCRIPTION "Entry for ppolicy amp element."
        INDEX       { diffServPolicyMapElementIndex }
        ::= { diffServPolicyMapElementTable 1 }

DiffServPolicyMapElementEntry ::= SEQUENCE
{
    diffServPolicyMapElementIndex           Integer32,
    diffServPolicyMapElementClassMapIndex   Integer32,
    diffServPolicyMapElementMeterIndex      Integer32,
    diffServPolicyMapElementActionIndex     Integer32,
    diffServPolicyMapElementStatus          RowStatus
}

diffServPolicyMapElementIndex OBJECT-TYPE
        SYNTAX      Integer32
        MAX-ACCESS  not-accessible
        STATUS      current
        DESCRIPTION "An index that uniquely identifies an entry in this
                     table."
        ::= { diffServPolicyMapElementEntry 1 }

diffServPolicyMapElementClassMapIndex OBJECT-TYPE
    SYNTAX      Integer32
    MAX-ACCESS  read-create
    STATUS      current
    DESCRIPTION "Specifies the class map binding to this entry.The class map
                 identified by a particular value of this index is associated
                 with the same diffServClassMapEntry as identified by the
                 same value of diffServClassMapIndex."
    ::= { diffServPolicyMapElementEntry 2 }

diffServPolicyMapElementMeterIndex OBJECT-TYPE
    SYNTAX      Integer32
    MAX-ACCESS  read-create
    STATUS      current
    DESCRIPTION "Specifies the meter binding to this entry.The meter
                 identified by a particular value of this index is associated
                 with the same diffServMeterEntry as identified by the same
                 value of diffServMeterIndex."
    ::= { diffServPolicyMapElementEntry 3 }

diffServPolicyMapElementActionIndex OBJECT-TYPE
    SYNTAX      Integer32
    MAX-ACCESS  read-create
    STATUS      current
    DESCRIPTION "Specifies the action binding to this entry.The action
                 identified by a particular value of this index is associated
                 with the same diffServActionEntry as identified by the same
                 value of diffServActionIndex."
    ::= { diffServPolicyMapElementEntry 4 }

diffServPolicyMapElementStatus OBJECT-TYPE
    SYNTAX      RowStatus
    MAX-ACCESS  read-create
    STATUS      current
    DESCRIPTION "This object is used to create a new row or modify or delete
                 an existing row in this table.The status column has six
                 defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServPolicyMapElementEntry 5 }




diffServClassMapTable OBJECT-TYPE
        SYNTAX      SEQUENCE OF DiffServClassMapEntry
        MAX-ACCESS  not-accessible
        STATUS      current
        DESCRIPTION "Table for class map."
        ::= { diffServMgt 13 }

diffServClassMapEntry OBJECT-TYPE
        SYNTAX      DiffServClassMapEntry
        MAX-ACCESS  not-accessible
        STATUS      current
        DESCRIPTION "Entry for class map."
        INDEX       { diffServClassMapIndex }
        ::= { diffServClassMapTable 1 }

DiffServClassMapEntry ::= SEQUENCE
{
    diffServClassMapIndex               Integer32,
    diffServClassMapName                DisplayString,
    diffServClassMapDescription         DisplayString,
    diffServClassMapMatchType           INTEGER,
    diffServClassMapElmentIndexTypeList OCTET STRING,
    diffServClassMapElmentIndexList     OCTET STRING,
    diffServClassMapStatus              RowStatus
}

diffServClassMapIndex OBJECT-TYPE
        SYNTAX      Integer32
        MAX-ACCESS  not-accessible
        STATUS      current
        DESCRIPTION "An index that uniquely identifies an entry in this
                     table."
        ::= { diffServClassMapEntry 1 }

diffServClassMapName OBJECT-TYPE
    SYNTAX      DisplayString (SIZE (1..16))
    MAX-ACCESS  read-create
    STATUS      current
    DESCRIPTION "The name of this entry."
    ::= { diffServClassMapEntry 2 }

diffServClassMapDescription OBJECT-TYPE
    SYNTAX      DisplayString (SIZE (0..64))
    MAX-ACCESS  read-create
    STATUS      current
    DESCRIPTION "The description of this entry."
    ::= { diffServClassMapEntry 3 }

diffServClassMapMatchType OBJECT-TYPE
    SYNTAX       INTEGER {
                     matchAny(1),
                     matchAll(2)
                }
    MAX-ACCESS  read-create
    STATUS      current
    DESCRIPTION "The map match type of this entry."
    ::= { diffServClassMapEntry 4 }

diffServClassMapElmentIndexTypeList OBJECT-TYPE
    SYNTAX      OCTET STRING (SIZE (0..255))
    MAX-ACCESS  read-only
    STATUS      current
    DESCRIPTION "The octet string containes the type of class map element
                 indexes. One octet expresses one type of the class map
                 elment index and it map the index of
                 differServClasssMapElmentIndexList in order.When type is
                 1(macAce), the maping index of
                 differServClasssMapElmentIndexList is the
                 diffServMacAceEntry.When type is 2(ipAce), the maping
                 index of differServClasssMapElmentIndexList is the
                 diffServIpAceEntry. When type is 3(acl), the maping
                 index of differServClasssMapElmentIndexList is the
                 diffServAclEntry. When type is 4(ipv6Ace), the maping
                 index of differServClasssMapElmentIndexList is the
                 diffServIpv6AceEntry."
    ::= { diffServClassMapEntry 5 }

diffServClassMapElmentIndexList OBJECT-TYPE
    SYNTAX      OCTET STRING (SIZE (0..255))
    MAX-ACCESS  read-only
    STATUS      current
    DESCRIPTION "The octet string containes the class map element indexes.One
                 octet expresses one index. This indexes list indicates the
                 particular class map elements which are belong to this table.
                 The class map element use type to indicate diffServAclEntry,
                 the diffServIpAceEntry of the MF, the diffServMacAceEntry of
                 the MF or the diffServIpv6AceEntry of the MF. The type is one
                 octet specified in differServClasssMapElmentIndexTypeList in
                 order. When type is 1(macAce), the maping index of
                 differServClasssMapElmentIndexList is the
                 diffServMacAceEntry.When type is 2(ipAce), the maping index
                 of differServClasssMapElmentIndexList is the
                 diffServIpAceEntry.When type is 3(acl), the maping index of
                 differServClasssMapElmentIndexList is the diffServAclEntry.
                 When type is 4(ipv6Ace), the maping index of
                 differServClasssMapElmentIndexList is the
                 diffServIpv6AceEntry."
    ::= { diffServClassMapEntry 6 }

diffServClassMapStatus OBJECT-TYPE
    SYNTAX      RowStatus
    MAX-ACCESS  read-create
    STATUS      current
    DESCRIPTION "This object is used to create a new row or modify or delete
                 an existing row in this table.The status column has six
                 defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB."
    ::= { diffServClassMapEntry 7 }



diffServClassMapAttachCtl  OBJECT IDENTIFIER   ::= { diffServMgt 14 }

diffServClassMapAttachCtlIndex OBJECT-TYPE
        SYNTAX      Integer32
        MAX-ACCESS  read-write
        STATUS      current
        DESCRIPTION "Specifies the class map as the target to relate with
                     class map elements. The class map identified by a
                     particular value of this index is associated with the
                     same diffServClassMapEntry as identified by the same
                     value of diffServClassMapIndex."
        ::= { diffServClassMapAttachCtl 1 }

diffServClassMapAttachCtlElmentIndexType OBJECT-TYPE
    SYNTAX    INTEGER {
                     macAce(1),
                     ipAce(2),
                     acl(3),
                     ipv6Ace(4)
                }
    MAX-ACCESS  read-write
    STATUS      current
    DESCRIPTION "Specifies the type of class map element to relate with the
                 class map. When type is 1(macAce), the index of
                 diffServClassMapAttachCtlElmentIndex is the index of
                 diffServMacAceEntry.When type is 2(ipAce), the index of
                 diffServClassMapAttachCtlElmentIndex is the index of
                 diffServIpAceEntry.When type is 3(acl), the index of
                 diffServClassMapAttachCtlElmentIndex is the index of
                 diffServAclEntry.When type is 4(ipv6Ace), the index of
                 diffServClassMapAttachCtlElmentIndex is the index of
                 diffServIpv6AceEntry."
    ::= { diffServClassMapAttachCtl 2 }

diffServClassMapAttachCtlElmentIndex OBJECT-TYPE
    SYNTAX      Integer32
    MAX-ACCESS  read-write
    STATUS      current
    DESCRIPTION "Specifies the class map element relate with the class map.
                 The class map element use type to indicate diffServAclEntry,
                 the diffServIpAceEntry of the MF, the diffServMacAceEntry of
                 the MF or the diffServIpv6AceEntry of the MF. The type is
                 specified in diffServClassMapAttachCtlElmentIndexType. When
                 type is 1(macAce), the maping index of
                 differServClasssMapElmentIndexList is the
                 diffServMacAceEntry.When type is 2(ipAce), the maping index
                 of differServClasssMapElmentIndexList is the
                 diffServIpAceEntry.When type is 3(acl), the maping index of
                 differServClasssMapElmentIndexList is the diffServAclEntry.
                 When type is 4(ipv6Ace), the maping index of
                 differServClasssMapElmentIndexList is the
                 diffServIpv6AceEntry."
    ::= { diffServClassMapAttachCtl 3 }

diffServClassMapAttachCtlAction OBJECT-TYPE
    SYNTAX      INTEGER
                    {
                        notAction(1),
                        attaching(2),
                        notAttaching(3)
                    }
    MAX-ACCESS  read-write
    STATUS      current
    DESCRIPTION "When setting this object to attach(2) to begin the attaching
                 operation, a particular class map element is attached to a
                 particular class map.When setting this object to notAttach(3)
                 to begin the not attaching operation, then a particular class
                 map element is not attached to a particular class map.When
                 action finsh or no action, the value of this object is
                 noAction(1), The value of a particular class map is
                 specified in the AclAttachCtlTargetIndex. The class map
                 element is specified by
                 diffServClassMapAttachCtlElmentIndexType and
                 diffServClassMapAttachCtlElmentIndex."
    ::= { diffServClassMapAttachCtl 4 }




diffServAclTable OBJECT-TYPE
        SYNTAX      SEQUENCE OF DiffServAclEntry
        MAX-ACCESS  not-accessible
        STATUS      current
        DESCRIPTION "Table for ACL."
        ::= { diffServMgt 15 }

diffServAclEntry OBJECT-TYPE
        SYNTAX      DiffServAclEntry
        MAX-ACCESS  not-accessible
        STATUS      current
        DESCRIPTION "Entry for ACL."
        INDEX       { diffServAclIndex }
        ::= { diffServAclTable 1 }

DiffServAclEntry ::= SEQUENCE
{
    diffServAclIndex        Integer32,
    diffServAclName         DisplayString,
    diffServAclAceIndexType INTEGER,
    diffServAclAceIndexList OCTET STRING,
    diffServAclStatus       RowStatus
}

diffServAclIndex OBJECT-TYPE
        SYNTAX      Integer32
        MAX-ACCESS  not-accessible
        STATUS      current
        DESCRIPTION "An index that uniquely identifies an entry in the acl
                     table."
        ::= { diffServAclEntry 1 }

diffServAclName OBJECT-TYPE
    SYNTAX      DisplayString (SIZE (1..16))
    MAX-ACCESS  read-create
    STATUS      current
    DESCRIPTION "The name of this entry."
    ::= { diffServAclEntry 2 }

diffServAclAceIndexType OBJECT-TYPE
    SYNTAX      INTEGER {
                     macAce(1),
                     ipAce(2),
                     ipv6Ace(3)
                }
    MAX-ACCESS  read-only
    STATUS      current
    DESCRIPTION "The type of this entry.When type is 1(macAce), the indexes
                 of diffServAclAceIndexList are the diffServMacAceEntry.
                 When type is 2(ipAce), the indexes of
                 diffServAclAceIndexList are the diffServIpAceEntry.When
                 type is 3(ipv6Ace), the indexes of diffServAclAceIndexList
                 are the diffServIpv6AceEntry."
    ::= { diffServAclEntry 3 }

diffServAclAceIndexList OBJECT-TYPE
    SYNTAX      OCTET STRING(SIZE (0..255))
    MAX-ACCESS  read-only
    STATUS      current
    DESCRIPTION "The octet string containes the ace indexes.One octet
                 expresses one index. This indexes list indicates the
                 particular aces which are belong to this table. The ace use
                 type to indicat the diffServIpAceEntry, the
                 diffServMacAceEntry or the diffServIpv6AceEntry. The type is
                 specified in diffServAclAceIndexType.When type is 1(macAce),
                 the index of diffServAclAceIndexList is the
                 diffServMacAceEntry.When type is 2(ipAce), the index of
                 diffServAclAceIndexList is the diffServIpAceEntry. When
                 type is 3(ipv6Ace), the index of diffServAclAceIndexList
                 is the diffServIpv6AceEntry."
    ::= { diffServAclEntry 4 }

diffServAclStatus OBJECT-TYPE
    SYNTAX      RowStatus
    MAX-ACCESS  read-create
    STATUS      current
    DESCRIPTION "This object is used to create a new row or modify or delete
                 an existing row in this table.
                 The status column has six defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServAclEntry 5 }


diffServAclAttachCtl  OBJECT IDENTIFIER   ::= { diffServMgt 16 }

diffServAclAttachCtlIndex OBJECT-TYPE
        SYNTAX      Integer32
        MAX-ACCESS  read-write
        STATUS      current
        DESCRIPTION "Specifies the acl as the target to relate with the ip
                     ace ,the mac ace or ipv6 ace. The acl identified by a
                     particular value of this index  is associated with the
                     same diffServAclEntry as identified by the same value
                     of diffServAclIndex."
        ::= { diffServAclAttachCtl 1 }

diffServAclAttachCtlAceType OBJECT-TYPE
    SYNTAX    INTEGER {
        macAce(1),
        ipAce(2),
        ipv6Ace(3)
    }
    MAX-ACCESS  read-write
    STATUS      current
    DESCRIPTION "Specifies the type of diffServAclAttachCtlAceIndex to relate
                 with the diffServAclAttachCtlIndex.When type is 1(macAce),
                 the index of diffServAclAceIndexList is the
                 diffServMacAceEntry.When type is 2(ipAce), the index of
                 diffServAclAceIndexList is the diffServIpAceEntry.When type
                 is 3(ipv6Ace), the index of diffServAclAceIndexList is the
                 diffServIpv6AceEntry."
    ::= { diffServAclAttachCtl 2 }

diffServAclAttachCtlAceIndex OBJECT-TYPE
    SYNTAX      Integer32
    MAX-ACCESS  read-write
    STATUS      current
    DESCRIPTION "Specifies the ace to relate with the
                 diffServAclAttachCtlIndex.When
                 diffServAclAttachCtlAceType is 1(macAce), the value of
                 diffServAclAttachCtlIndex is the diffServMacAceEntry.When
                 diffServAclAttachCtlAceType is 2(ipAce), the value of
                 diffServAclAttachCtlIndex is the diffServIpAceEntry.When
                 diffServAclAttachCtlAceType is 3(ipv6Ace), the value of
                 diffServAclAttachCtlIndex is the diffServIpv6AceEntry."
    ::= { diffServAclAttachCtl 3 }


diffServAclAttachCtlAction OBJECT-TYPE
    SYNTAX      INTEGER
                    {
                        notAction(1),
                        attaching(2),
                        notAttaching(3)
                    }
    MAX-ACCESS  read-write
    STATUS      current
    DESCRIPTION "When setting this object to attach(2) to begin the attaching
                 operation, a particular ace are attached to a particular
                 acl. When setting this object to notAttach(3) to begin the
                 not attaching operation, then a particular ace are not
                 attached to a particular acl. When action finsh or no
                 action, the value of this object is noAction(1), The
                 value of a   particular acl is specified in the
                 diffServAclAttachCtlAceType and diffServAclAttachCtlAceIndex."
    ::= { diffServAclAttachCtl 4 }


diffServIpAceTable OBJECT-TYPE
        SYNTAX      SEQUENCE OF DiffServIpAceEntry
        MAX-ACCESS  not-accessible
        STATUS      current
        DESCRIPTION "Table for IP ACE."
        ::= { diffServMgt 17 }

diffServIpAceEntry OBJECT-TYPE
        SYNTAX      DiffServIpAceEntry
        MAX-ACCESS  not-accessible
        STATUS      current
        DESCRIPTION "Entry for IP ACE."
        INDEX       { diffServIpAceIndex }
        ::= { diffServIpAceTable 1 }

DiffServIpAceEntry ::= SEQUENCE
{
    diffServIpAceIndex                  Integer32,
    diffServIpAceAccess                 INTEGER,
    diffServIpAceSourceIpAddr           IpAddress,
    diffServIpAceSourceIpAddrBitmask    IpAddress,
    diffServIpAceDestIpAddr             IpAddress,
    diffServIpAceDestIpAddrBitmask      IpAddress,
    diffServIpAceProtocol               Integer32,
    diffServIpAcePrec                   Integer32,
    diffServIpAceTos                    Integer32,
    diffServIpAceDscp                   Integer32,
    diffServIpAceSourcePortOp           INTEGER,
    diffServIpAceMinSourcePort          Integer32,
    diffServIpAceMaxSourcePort          Integer32,
    diffServIpAceSourcePortBitmask      Integer32,
    diffServIpAceDestPortOp             INTEGER,
    diffServIpAceMinDestPort            Integer32,
    diffServIpAceMaxDestPort            Integer32,
    diffServIpAceDestPortBitmask        Integer32,
    diffServIpAceControlCode            Integer32,
    diffServIpAceControlCodeBitmask     Integer32,
    diffServIpAceStatus RowStatus
}

diffServIpAceIndex OBJECT-TYPE
        SYNTAX      Integer32
        MAX-ACCESS  not-accessible
        STATUS      current
        DESCRIPTION "An index that uniquely identifies an entry in the ip ace
                     table."
        ::= { diffServIpAceEntry 1 }

diffServIpAceAccess OBJECT-TYPE
    SYNTAX  INTEGER {
        permit(1),
        deny(2)
    }
    MAX-ACCESS  read-create
    STATUS      current
    DESCRIPTION "Indicates the action to be taken if a packet matches this
                 ACE."
    ::= { diffServIpAceEntry 2 }

diffServIpAceSourceIpAddr OBJECT-TYPE
    SYNTAX      IpAddress
    MAX-ACCESS  read-create
    STATUS      current
    DESCRIPTION "The specified source IP address. The packet's source address
                 is AND-ed with the value of IpAceSourceIpAddrBitmask and
                 then compared against the value of this object."
    ::= { diffServIpAceEntry 3 }

diffServIpAceSourceIpAddrBitmask OBJECT-TYPE
    SYNTAX      IpAddress
    MAX-ACCESS  read-create
    STATUS      current
    DESCRIPTION "The specified source IP address mask. The packet's source
                 address is AND-ed with the value of IpAceSourceIpAddr and
                 then compared against the value of this object."
    ::= { diffServIpAceEntry 4 }

diffServIpAceDestIpAddr OBJECT-TYPE
    SYNTAX      IpAddress
    MAX-ACCESS  read-create
    STATUS      current
    DESCRIPTION "The specified destination IP address. The packet's
                 destination address is AND-ed with the value of
                 diffServIpAceDestIpAddrBitmask and then compared against
                 the value of this object."
    ::= { diffServIpAceEntry 5 }

diffServIpAceDestIpAddrBitmask OBJECT-TYPE
        SYNTAX      IpAddress
        MAX-ACCESS  read-create
        STATUS      current
        DESCRIPTION "The specified destination IP address mask."
        ::= { diffServIpAceEntry 6 }

diffServIpAceProtocol OBJECT-TYPE
    SYNTAX      Integer32(0..255)
    MAX-ACCESS  read-create
    STATUS      current
    DESCRIPTION "The protocol number field in the IP header used to indicate
                 the higher layer protocol as specified in RFC 1700. A value
                 value of 0 matches every IP packet. The object=256, means
                 'any' For example : 0 is IP, 1 is ICMP, 2 is IGMP, 4 is IP
                 in IP encapsulation, 6 is TCP, 9 is IGRP, 17 is UDP, 47 is
                 GRE, 50 is ESP, 51 is AH, 88 is IGRP, 89 is OSPF, 94 is
                 KA9Q/NOS compatible IP over IP, 103 is PIMv2, 108 is PCP."
    ::= { diffServIpAceEntry 7 }

diffServIpAcePrec OBJECT-TYPE
    SYNTAX      Integer32(0..7)
    MAX-ACCESS  read-create
    STATUS      current
    DESCRIPTION "Specifies the IP precedence value to be matched against.
                 The value of this object is ignored whenever the value of
                 diffServIpAcePrec object is 8."
    ::= { diffServIpAceEntry 8 }

diffServIpAceTos OBJECT-TYPE
    SYNTAX      Integer32(0..15)
    MAX-ACCESS  read-create
    STATUS      current
    DESCRIPTION "Specifies the IP ToS facility value to be matched against.
                 The value of this object is ignored whenever the value of
                 diffServIpAcePrec object is 9."
    ::= { diffServIpAceEntry 9 }

diffServIpAceDscp OBJECT-TYPE
    SYNTAX      Integer32(0..63)
    MAX-ACCESS  read-create
    STATUS      current
    DESCRIPTION "Specifies the DSCP value to be matched against. The value
                 of this object is ignored whenever the value of
                 diffServIpAcePrec object is 64."
    ::= { diffServIpAceEntry 10 }

diffServIpAceSourcePortOp OBJECT-TYPE
    SYNTAX  INTEGER {
                noOperator(1),
                equal(2),
                range(3)
    }
    MAX-ACCESS  read-create
    STATUS      current
    DESCRIPTION "Indicates how a packet's source TCP/UDP port number is to be
                 compared. noOperator(1), which is the default value, means
                 no comparison is to be made with the source TCP/UDP port
                 number."
    ::= { diffServIpAceEntry 11 }

diffServIpAceMinSourcePort OBJECT-TYPE
        SYNTAX      Integer32(0..'FFFF'h)
        MAX-ACCESS  not-accessible
        STATUS      current
        DESCRIPTION "If the diffServIpAceSourcePortOp is range(3), this
                     indicates the lower bound of the TCP/UDP port number
                     value range."
        ::= { diffServIpAceEntry 12 }

diffServIpAceMaxSourcePort OBJECT-TYPE
    SYNTAX      Integer32(0..'FFFF'h)
    MAX-ACCESS  read-create
    STATUS      current
    DESCRIPTION "If the diffServIpAceSourcePortOp is range(3), this indicates
                 the upper bound of the TCP/UDP port number value range."
    ::= { diffServIpAceEntry 13 }

diffServIpAceSourcePortBitmask OBJECT-TYPE
    SYNTAX      Integer32(0..'FFFF'h)
    MAX-ACCESS  read-create
    STATUS      current
    DESCRIPTION "If the diffServIpAceSourcePortOp is equal(2), this indicates
                 the bitmask of the diffServIpAceMinSourcePort."
    ::= { diffServIpAceEntry 14 }

diffServIpAceDestPortOp OBJECT-TYPE
    SYNTAX      INTEGER{
                noOperator(1),
                equal(2),
                range(3)
    }
    MAX-ACCESS  read-create
    STATUS      current
    DESCRIPTION "Indicates how a packet's destination TCP/UDP port number is
                 to be compared. noOperator(1), which is the default value,
                 means that no comparison is to be made with the destination
                 TCP/UDP port number."
    ::= { diffServIpAceEntry 15 }

diffServIpAceMinDestPort OBJECT-TYPE
    SYNTAX      Integer32(0..'FFFF'h)
    MAX-ACCESS  read-create
    STATUS      current
    DESCRIPTION "If the diffServIpAceDestPortOp is range(3), this indicates
                 the lower bound of the TCP/UDP port number value range."
    ::= { diffServIpAceEntry 16 }

diffServIpAceMaxDestPort OBJECT-TYPE
    SYNTAX      Integer32(0..'FFFF'h)
    MAX-ACCESS  read-create
    STATUS      current
    DESCRIPTION "If the diffServIpAceDestPortOp is range(3), this indicates
                 the upper bound of the TCP/UDP
                 port number value range."
    ::= { diffServIpAceEntry 17 }

diffServIpAceDestPortBitmask OBJECT-TYPE
    SYNTAX      Integer32(0..'FFFF'h)
    MAX-ACCESS  read-create
    STATUS      current
    DESCRIPTION "If the diffServIpAceDestPortOp is equal(2), this indicates
                 the bitmask of the diffServIpAceMinDestPort."
    ::= { diffServIpAceEntry 18 }

diffServIpAceControlCode OBJECT-TYPE
    SYNTAX      Integer32(0..63)
    MAX-ACCESS  read-create
    STATUS      current
    DESCRIPTION "Indicates how the control flags of TCP packets are to be
                 compared. diffServIpAceControlCode is AND-ed with
                 diffServIpAceControlCodeBitmask"
    ::= { diffServIpAceEntry 19 }

diffServIpAceControlCodeBitmask OBJECT-TYPE
    SYNTAX      Integer32(0..63)
    MAX-ACCESS  read-create
    STATUS      current
    DESCRIPTION "Indicates how the control flags of TCP packets are to be
                 compared. It can be used to check multiple flags of the FIN,
                 SYN, RST, PSH, ACK, URG by the sum of FIN=1, SYN=2, RST=4,
                 PSH=8, ACK=16, URG=32."
    ::= { diffServIpAceEntry 20 }

diffServIpAceStatus OBJECT-TYPE
    SYNTAX      RowStatus
    MAX-ACCESS  read-create
    STATUS      current
    DESCRIPTION "This object is used to create a new row or modify or delete
                 an existing row in this table.
                 The status column has six defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServIpAceEntry 21 }

diffServMacAceTable OBJECT-TYPE
        SYNTAX      SEQUENCE OF DiffServMacAceEntry
        MAX-ACCESS  not-accessible
        STATUS      current
        DESCRIPTION "Table for Mac Ace."
        ::= { diffServMgt 18 }

diffServMacAceEntry OBJECT-TYPE
        SYNTAX      DiffServMacAceEntry
        MAX-ACCESS  not-accessible
        STATUS      current
        DESCRIPTION "Entry for Mac Ace."
        INDEX       { diffServMacAceIndex }
        ::= { diffServMacAceTable 1 }

DiffServMacAceEntry ::= SEQUENCE
{
    diffServMacAceIndex                 Integer32,
    diffServMacAceAccess                INTEGER,
    diffServMacAcePktformat             INTEGER,
    diffServMacAceSourceMacAddr         MacAddress,
    diffServMacAceSourceMacAddrBitmask  MacAddress,
    diffServMacAceDestMacAddr           MacAddress,
    diffServMacAceDestMacAddrBitmask    MacAddress,
    diffServMacAceVidOp                 INTEGER,
    diffServMacAceMinVid                Integer32,
    diffServMacAceVidBitmask            Integer32,
    diffServMacAceMaxVid                Integer32,
    diffServMacAceEtherTypeOp           INTEGER,
    diffServMacAceEtherTypeBitmask      Integer32,
    diffServMacAceMinEtherType          Integer32,
    diffServMacAceMaxEtherType          Integer32,
    diffServMacAceStatus                RowStatus
}

diffServMacAceIndex OBJECT-TYPE
        SYNTAX      Integer32
        MAX-ACCESS  not-accessible
        STATUS      current
        DESCRIPTION "An index that uniquely identifies an entry in the mac
                     ace table."
        ::= { diffServMacAceEntry 1 }

diffServMacAceAccess OBJECT-TYPE
        SYNTAX    INTEGER {
            permit(1),
            deny(2)
        }
        MAX-ACCESS  read-create
        STATUS      current
        DESCRIPTION "Indicates the action to be taken if a packet matches
                     this ACE."
        ::= { diffServMacAceEntry 2 }

diffServMacAcePktformat OBJECT-TYPE
    SYNTAX    INTEGER {
        any(1),
        untagged-Eth2(2),
        untagged802Dot3(3),
        tagggedEth2(4),
        tagged802Dot3(5)
    }
    MAX-ACCESS  read-create
    STATUS      current
    DESCRIPTION "Used to check the packet format of the packets. This object
                 cannot be configured when the status of the entry,
                 diffServMacAceStatus, is active(1)."
    ::= { diffServMacAceEntry 3 }

diffServMacAceSourceMacAddr OBJECT-TYPE
    SYNTAX      MacAddress
    MAX-ACCESS  read-create
    STATUS      current
    DESCRIPTION "Indicates the 48-bit source MAC address. The specified
                 source MAC of the packet The packet's source MAC address
                 is AND-ed with the value of
                 diffServMacAceSourceMacAddrBitmask and then compared against
                 the value of this object. "
    ::= { diffServMacAceEntry 4 }

diffServMacAceSourceMacAddrBitmask OBJECT-TYPE
    SYNTAX      MacAddress
    MAX-ACCESS  read-create
    STATUS      current
    DESCRIPTION "The specified source MAC address mask."
    ::= { diffServMacAceEntry 5 }

diffServMacAceDestMacAddr OBJECT-TYPE
    SYNTAX      MacAddress
    MAX-ACCESS  read-create
    STATUS      current
    DESCRIPTION "Indicates the 48-bit destination MAC address. The specified
                 destination MAC of the packet. The packet's destination MAC
                 address is AND-ed with the value of
                 diffServMacAceDestMacAddrBitmask and then compared against
                 the value of this object."
    ::= { diffServMacAceEntry 6 }

diffServMacAceDestMacAddrBitmask OBJECT-TYPE
    SYNTAX      MacAddress
    MAX-ACCESS  read-create
    STATUS      current
    DESCRIPTION "The specified destination MAC address mask."
    ::= { diffServMacAceEntry 7 }

diffServMacAceVidOp OBJECT-TYPE
    SYNTAX    INTEGER {
            noOperator(1),
            equal(2),
            range(3)
        }
        MAX-ACCESS  read-create
        STATUS      current
        DESCRIPTION "Indicates how a packet's vid is to be compared. This
                     object cannot be configured when the status of the entry,
                     diffServMacAceStatus, is active(1)."
        ::= { diffServMacAceEntry 8 }

diffServMacAceMinVid OBJECT-TYPE
    SYNTAX      Integer32(1..4093)
    MAX-ACCESS  read-create
    STATUS      current
    DESCRIPTION "Indicates the lower bound of the vid value range if the
                 diffServMacAceVidOp is range(3)."
    ::= { diffServMacAceEntry 9 }

diffServMacAceVidBitmask OBJECT-TYPE
    SYNTAX      Integer32(0..'0FFF'h)
    MAX-ACCESS  read-create
    STATUS      current
    DESCRIPTION "The bitmask of vid if the diffServMacAceVidOp is equal,
                 default value is 0xfff."
    ::= { diffServMacAceEntry 10 }

diffServMacAceMaxVid OBJECT-TYPE
    SYNTAX      Integer32(1..4093)
    MAX-ACCESS  read-create
    STATUS      current
    DESCRIPTION "Indicates the upper bound of the vid value range if the
                 diffServMacAceVidOp is range(3). This object cannot be
                 configured when the status of the entry,
                 diffServMacAceStatus,
                 is active(1)."
    ::= { diffServMacAceEntry 11 }

diffServMacAceEtherTypeOp OBJECT-TYPE
    SYNTAX    INTEGER {
        noOperator(1),
        equal(2),
        range(3)
    }
    MAX-ACCESS  read-create
    STATUS      current
    DESCRIPTION "Indicates how a packet's ether type is to be compared."
    ::= { diffServMacAceEntry 12 }

diffServMacAceEtherTypeBitmask OBJECT-TYPE
    SYNTAX      Integer32(0..'FFFF'h)
    MAX-ACCESS  read-create
    STATUS      current
    DESCRIPTION "The bitmask of ether type if the diffServMacAceEtherTypeOp
                 is equal(2) , default value is 0xFFFF."
    ::= { diffServMacAceEntry 13 }

diffServMacAceMinEtherType OBJECT-TYPE
        SYNTAX      Integer32('0600'h..'FFFF'h)
        MAX-ACCESS  read-create
        STATUS      current
        DESCRIPTION "Indicates the lower bound of the ether type value range
                     if the diffServMacAceEtherTypeOp is range(3)."
        ::= { diffServMacAceEntry 14 }

diffServMacAceMaxEtherType OBJECT-TYPE
    SYNTAX      Integer32('0600'h..'FFFF'h)
    MAX-ACCESS  read-create
    STATUS      current
    DESCRIPTION "Indicates the upper bound of the ether type value range if
                 the diffServMacAceEtherTypeOp is range(3)."
    ::= { diffServMacAceEntry 15 }

diffServMacAceStatus OBJECT-TYPE
    SYNTAX      RowStatus
    MAX-ACCESS  read-create
    STATUS      current
    DESCRIPTION "This object is used to create a new row or modify or delete
                 an existing row in this table.
                 The status column has six defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServMacAceEntry 16 }

diffServMacAceCosOp OBJECT-TYPE
    SYNTAX    INTEGER {
        noOperator(1),
        equal(2),
        range(3)
    }
    MAX-ACCESS  read-create
    STATUS      current
    DESCRIPTION "Indicates how a packet's CoS is compared.
                 If the object type of diffServMacAceCosOp is equal(2),
                 diffServMacAceMinCos indicates the CoS value for comparing, and
                 diffServMacAceCosBitmask is used as the bitmask of the CoS value.
                 If the object type of diffServMacAceCosOp is range(3),
                 diffServMacAceMinCos should be used as the lower bound of the CoS value."

    ::= { diffServMacAceEntry 17 }

diffServMacAceCosBitmask OBJECT-TYPE
    SYNTAX      INTEGER ('0'h..'7'h)
    MAX-ACCESS  read-create
    STATUS      current
    DESCRIPTION "Indicates the bitmask of the CoS value if the object type of
                 diffServMacAceCosOp is equal(2). The default value is 0."
    ::= { diffServMacAceEntry 18 }

diffServMacAceMinCos OBJECT-TYPE
        SYNTAX      INTEGER ('0'h..'7'h)
        MAX-ACCESS  read-create
        STATUS      current
        DESCRIPTION "If the object type of diffServMacAceCosOp is equal(2),
                     diffServMacAceMinCos indicates the CoS value for comparing.
                     If the object type of diffServMacAceCosOp is range(3),
                     diffServMacAceMinCos indicates the lower bound of the CoS value."
    ::= { diffServMacAceEntry 19 }

diffServActionTable OBJECT-TYPE
        SYNTAX      SEQUENCE OF DiffServActionEntry
        MAX-ACCESS  not-accessible
        STATUS      current
        DESCRIPTION "Table for action."
        ::= { diffServMgt 19 }

diffServActionEntry OBJECT-TYPE
        SYNTAX      DiffServActionEntry
        MAX-ACCESS  not-accessible
        STATUS      current
        DESCRIPTION "Entry for action."
        INDEX       { diffServActionIndex }
        ::= { diffServActionTable 1 }

DiffServActionEntry ::= SEQUENCE
{
    diffServActionIndex                 Integer32,
    diffServActionPktNewPri             Integer32,
    diffServActionPktNewTos             Integer32,
    diffServActionPktNewDscp            Integer32,
    diffServActionRedPktNewDscp         Integer32,
    diffServActionYellowPktNewDscp      Integer32,
    diffServActionDropPrecedence        Integer32,
    diffServActionRedDropPrecedence     Integer32,
    diffServActionYellowDropPrecedence  Integer32,
    diffServActionMeterMode             INTEGER,
    diffServActionStatus                RowStatus
}

diffServActionIndex OBJECT-TYPE
        SYNTAX      Integer32
        MAX-ACCESS  not-accessible
        STATUS      current
        DESCRIPTION "An index that uniquely identifies an entry in the action
                     table."
        ::= { diffServActionEntry 1 }

diffServActionPktNewPri OBJECT-TYPE
        SYNTAX      Integer32(0..7)
        MAX-ACCESS  read-create
        STATUS      current
        DESCRIPTION "Specifies the new priority value to the action of
                     packet."
        ::= { diffServActionEntry 2 }

diffServActionPktNewTos  OBJECT-TYPE
        SYNTAX      Integer32(0..15)
        MAX-ACCESS  read-create
        STATUS      current
        DESCRIPTION "Specifies the new ToS facility value to the action of
                     packett."
        ::= { diffServActionEntry 3 }

diffServActionPktNewDscp OBJECT-TYPE
        SYNTAX      Integer32(0..63)
        MAX-ACCESS  read-create
        STATUS      current
        DESCRIPTION "Specifies the new DSCP value to the action of packet."
        ::= { diffServActionEntry 4 }

diffServActionRedPktNewDscp OBJECT-TYPE
        SYNTAX      Integer32(0..63)
        MAX-ACCESS  read-create
        STATUS      current
        DESCRIPTION "Specifies the new DSCP value to the action of red
                     packet."
        ::= { diffServActionEntry 5 }

diffServActionYellowPktNewDscp OBJECT-TYPE
        SYNTAX      Integer32(0..63)
        MAX-ACCESS  read-create
        STATUS      current
        DESCRIPTION "Specifies the new DSCP value to the action of yellow
                     packet."
        ::= { diffServActionEntry 6 }

diffServActionDropPrecedence OBJECT-TYPE
        SYNTAX      Integer32
        MAX-ACCESS  read-create
        STATUS      current
        DESCRIPTION "Specifies the new precedence value to the action of drop packet."
        ::= { diffServActionEntry 7 }

diffServActionRedDropPrecedence OBJECT-TYPE
        SYNTAX      Integer32
        MAX-ACCESS  read-create
        STATUS      current
        DESCRIPTION "Specifies the new precedence value to the action of red
                     drop packet."
        ::= { diffServActionEntry 8 }

diffServActionYellowDropPrecedence OBJECT-TYPE
        SYNTAX      Integer32
        MAX-ACCESS  read-create
        STATUS      current
        DESCRIPTION "Specifies the new precedence value to the action of
                     yellow drop packet."
        ::= { diffServActionEntry 9 }

diffServActionMeterMode  OBJECT-TYPE
    SYNTAX    INTEGER {
            default(1),
            flow(2),
            trTcmColorBlind(3),
            trTcmColorAware(4),
            srTcmColorBlind(5),
            srTcmColorAware(6)
        }
        MAX-ACCESS  read-create
        STATUS      current
        DESCRIPTION "Specifies the meter mode of the action."
        ::= { diffServActionEntry 10 }

diffServActionStatus OBJECT-TYPE
        SYNTAX      RowStatus
        MAX-ACCESS  read-create
        STATUS      current
        DESCRIPTION "This object is used to create a new row or modify or
                     delete an existing row in this table.
                 The status column has six defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
        ::= { diffServActionEntry 11 }

diffServMeterTable OBJECT-TYPE
        SYNTAX      SEQUENCE OF DiffServMeterEntry
        MAX-ACCESS  not-accessible
        STATUS      current
        DESCRIPTION "Table for meter."
        ::= { diffServMgt 20 }

diffServMeterEntry OBJECT-TYPE
        SYNTAX      DiffServMeterEntry
        MAX-ACCESS  not-accessible
        STATUS      current
        DESCRIPTION "Entry for meter."
        INDEX       { diffServActionIndex }
        ::= { diffServMeterTable 1 }

DiffServMeterEntry ::= SEQUENCE
{
    diffServMeterIndex      Integer32,
    diffServMeterModel      INTEGER,
    diffServMeterRate       Integer32,
    diffServMeterBurstSize  Integer32,
    diffServMeterInterval   Integer32,
    diffServMeterStatus     RowStatus
}

diffServMeterIndex OBJECT-TYPE
        SYNTAX      Integer32
        MAX-ACCESS  not-accessible
        STATUS      current
        DESCRIPTION "An entry that describes a single set of token bucket
                     parameters."
        ::= { diffServMeterEntry 1 }

diffServMeterModel OBJECT-TYPE
    SYNTAX    INTEGER {
            default(1),
            flow(2),
            trTcmColorBlind(3),
            trTcmColorAware(4),
            srTcmColorBlind(5),
            srTcmColorAware(6)
        }
    MAX-ACCESS  read-create
    STATUS      current
    DESCRIPTION "The Metering algorithm associated with the Token Bucket
                 parameters.  zeroDotZero indicates this is unknown."

    ::= { diffServMeterEntry 2 }

diffServMeterRate OBJECT-TYPE
    SYNTAX      Integer32(1..100000)
    MAX-ACCESS  read-create
    STATUS      current
    DESCRIPTION "The token-bucket rate, in kilobits per second (kbps)."
    ::= { diffServMeterEntry 3 }

diffServMeterBurstSize OBJECT-TYPE
    SYNTAX      Integer32(64..1522)
    MAX-ACCESS  read-create
    STATUS      current
    DESCRIPTION "The maximum number of bytes in a single transmission burst."
    ::= { diffServMeterEntry 4 }

diffServMeterInterval OBJECT-TYPE
    SYNTAX      Integer32
    MAX-ACCESS  read-create
    STATUS      current
    DESCRIPTION "The time interval used with the token bucket. "
    ::= { diffServMeterEntry 5 }

diffServMeterStatus OBJECT-TYPE
    SYNTAX      RowStatus
    MAX-ACCESS  read-create
    STATUS      current
    DESCRIPTION "This object is used to create a new row or modify or delete
                 an existing row in this table.
                 The status column has six defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServMeterEntry 6 }

diffServIpv6AceTable OBJECT-TYPE
        SYNTAX      SEQUENCE OF DiffServIpv6AceEntry
        MAX-ACCESS  not-accessible
        STATUS      current
        DESCRIPTION "Table for Ipv6 Ace."
        ::= { diffServMgt 21 }

diffServIpv6AceEntry OBJECT-TYPE
        SYNTAX      DiffServIpv6AceEntry
        MAX-ACCESS  not-accessible
        STATUS      current
        DESCRIPTION "Entry fo Ipv6 Ace."
        INDEX       { diffServIpv6AceIndex }
        ::= { diffServIpv6AceTable 1 }

DiffServIpv6AceEntry ::= SEQUENCE
{
   diffServIpv6AceIndex                 Integer32,
   diffServIpv6AceAccess                INTEGER,
   diffServIpv6AceSourceIpAddr          OCTET STRING,
   diffServIpv6AceSourceIpAddrPrefixLen Integer32,
   diffServIpv6AceDestIpAddr            OCTET STRING,
   diffServIpv6AceDestIpAddrPrefixLen   Integer32,
   diffServIpv6AceNextHeader            Integer32,
   diffServIpv6AceDscp                  Integer32,
   diffServIpv6AceFlowLabel             Unsigned32,
   diffServIpv6AceStatus                RowStatus
}

diffServIpv6AceIndex OBJECT-TYPE
        SYNTAX      Integer32
        MAX-ACCESS  not-accessible
        STATUS      current
        DESCRIPTION "An index that uniquely identifies an entry in the IPv6
                     table."
        ::= { diffServIpv6AceEntry 1 }

diffServIpv6AceAccess OBJECT-TYPE
    SYNTAX  INTEGER {
        permit(1),
        deny(2)
    }
    MAX-ACCESS  read-create
    STATUS      current
    DESCRIPTION "Indicates the action to be taken if a packet matches this
                 ACE."
    ::= { diffServIpv6AceEntry 2 }

diffServIpv6AceSourceIpAddr OBJECT-TYPE
    SYNTAX      OCTET STRING(SIZE (0..16))
    MAX-ACCESS  read-create
    STATUS      current
    DESCRIPTION "Specifies the source IPv6 address."
    ::= { diffServIpv6AceEntry 3 }

diffServIpv6AceSourceIpAddrPrefixLen OBJECT-TYPE
    SYNTAX      Integer32(0..63)
    MAX-ACCESS  read-create
    STATUS      current
    DESCRIPTION "The length (in bits) associated with the source IPv6 address
                 prefix of this entry."
    ::= { diffServIpv6AceEntry 4 }

diffServIpv6AceDestIpAddr OBJECT-TYPE
    SYNTAX      OCTET STRING (SIZE (0..16))
    MAX-ACCESS  read-create
    STATUS      current
    DESCRIPTION "Specifies the destination IPv6 address."
    ::= { diffServIpv6AceEntry 5 }

diffServIpv6AceDestIpAddrPrefixLen OBJECT-TYPE
    SYNTAX      Integer32(0..63)
    MAX-ACCESS  read-create
    STATUS      current
    DESCRIPTION "The length (in bits) associated with the destination IPv6
                 address prefix of this entry."
    ::= { diffServIpv6AceEntry 6 }

diffServIpv6AceNextHeader OBJECT-TYPE
    SYNTAX      Integer32(0..255)
    MAX-ACCESS  read-create
    STATUS      current
    DESCRIPTION "Specifies the Ipv6 next header."
    ::= { diffServIpv6AceEntry 7 }

diffServIpv6AceDscp OBJECT-TYPE
    SYNTAX      Integer32(0..64)
    MAX-ACCESS  read-create
    STATUS      current
    DESCRIPTION "Specifies the DSCP value to be matched against."
    ::= { diffServIpv6AceEntry 8 }

diffServIpv6AceFlowLabel OBJECT-TYPE
    SYNTAX      Unsigned32('00000000'h..'FFFFFFFF'h)
    MAX-ACCESS  read-create
    STATUS      current
    DESCRIPTION "Specifies the Ipv6 flow labe."
    ::= { diffServIpv6AceEntry 9 }

diffServIpv6AceStatus OBJECT-TYPE
    SYNTAX      RowStatus
    MAX-ACCESS  read-create
    STATUS      current
    DESCRIPTION "This object is used to create a new row or modify or delete
                 an existing row in this table.
                 The status column has six defined values:

                 The status column has six defined values:

                      - 'active', which indicates that the conceptual row is
                      available for use by the managed device;

                      - 'notInService', which indicates that the conceptual
                      row exists in the agent, but is unavailable for use by
                      the managed device (see NOTE below);

                      - 'notReady', which indicates that the conceptual row
                      exists in the agent, but is missing information
                      necessary in order to be available for use by the
                      managed device;

                      - 'createAndGo', which is supplied by a management
                      station wishing to create a new instance of a
                      conceptual row and to have its status automatically set
                      to active, making it available for use by the managed
                      device;

                      - 'createAndWait', which is supplied by a management
                      station wishing to create a new instance of a
                      conceptual row (but not make it available for use by
                      the managed device); and,

                      - 'destroy', which is supplied by a management station
                      wishing to delete all of the instances associated with
                      an existing conceptual row.

                 Whereas five of the six values (all except 'notReady') may
                 be specified in a management protocol set operation, only
                 three values will be returned in response to a management
                 protocol retrieval operation:  'notReady', 'notInService' or
                 'active'.  That is, when queried, an existing conceptual row
                 has only three states:  it is either available for use by
                 the managed device (the status column has value 'active');
                 it is not available for use by the managed device, though
                 the agent has sufficient information to make it so (the
                 status column has value 'notInService'); or, it is not
                 available for use by the managed device, and an attempt to
                 make it so would fail because the agent has insufficient
                 information (the state column has value 'notReady').

                 For a detailed description of this object, please refer to
                 SNMPv2-TC MIB.
                 "
    ::= { diffServIpv6AceEntry 10 }

diffServMultiFieldClfrCriteriaTable OBJECT-TYPE
        SYNTAX      SEQUENCE OF DiffServMultiFieldClfrCriteriaEntry
        MAX-ACCESS  not-accessible
        STATUS      current
        DESCRIPTION
            "The conceptual table of diffServMultiFieldClfrCriteriaTable."
        ::= { diffServMgt 22 }

diffServMultiFieldClfrCriteriaEntry OBJECT-TYPE
        SYNTAX      DiffServMultiFieldClfrCriteriaEntry
        MAX-ACCESS  not-accessible
        STATUS      current
        DESCRIPTION
            "The conceptual row for diffServMultiFieldClfrCriteriaEntry."
        AUGMENTS        {diffServMultiFieldClfrEntry}
        ::= { diffServMultiFieldClfrCriteriaTable 1 }

DiffServMultiFieldClfrCriteriaEntry ::= SEQUENCE
{
    diffServMultiFieldClfrCriteriaType               INTEGER,
    diffServMultiFieldClfrCriteriaInetAddressType    InetAddressType,
    diffServMultiFieldClfrCriteriaSrcInetAddress     InetAddress,
    diffServMultiFieldClfrCriteriaDstInetAddress     InetAddress,
    diffServMultiFieldClfrCriteriaMacSrc             MacAddress,
    diffServMultiFieldClfrCriteriaMacDst             MacAddress
}

diffServMultiFieldClfrCriteriaType OBJECT-TYPE
        SYNTAX      INTEGER
                    {
                        mac(1),
                        ipv4(2)
                    }
        MAX-ACCESS  read-create
        STATUS      current
        DESCRIPTION
            "The value indicates the entry is used to classify MAC frames or IP packets."
        ::= { diffServMultiFieldClfrCriteriaEntry 1 }

diffServMultiFieldClfrCriteriaInetAddressType OBJECT-TYPE
        SYNTAX      InetAddressType
        MAX-ACCESS  read-create
        STATUS      current
        DESCRIPTION
            "The IP address type used by this classifier entry.
             This object is limited to IPv4 address."
        ::= { diffServMultiFieldClfrCriteriaEntry 2 }

diffServMultiFieldClfrCriteriaSrcInetAddress OBJECT-TYPE
        SYNTAX      InetAddress
        MAX-ACCESS  read-create
        STATUS      current
        DESCRIPTION
            "The IP address to match against the packet's source Internet address"
        ::= { diffServMultiFieldClfrCriteriaEntry 3 }

diffServMultiFieldClfrCriteriaDstInetAddress OBJECT-TYPE
        SYNTAX      InetAddress
        MAX-ACCESS  read-create
        STATUS      current
        DESCRIPTION
            "The IP address to match against the packet's destination Internet address"
        ::= { diffServMultiFieldClfrCriteriaEntry 4 }

diffServMultiFieldClfrCriteriaMacSrc OBJECT-TYPE
        SYNTAX      MacAddress
        MAX-ACCESS  read-create
        STATUS      current
        DESCRIPTION
            "The frame address to match against the frame source address"
        ::= { diffServMultiFieldClfrCriteriaEntry 5 }

diffServMultiFieldClfrCriteriaMacDst OBJECT-TYPE
        SYNTAX      MacAddress
        MAX-ACCESS  read-create
        STATUS      current
        DESCRIPTION
            "The frame address to match against the frame destination address"
        ::= { diffServMultiFieldClfrCriteriaEntry 6 }

trafficShaperMgt             OBJECT IDENTIFIER ::= { qosMgt 5 }

--
-- trafficShaperPortTable
--

trafficShaperPortTable   OBJECT-TYPE
    SYNTAX      SEQUENCE OF TrafficShaperPortEntry
    MAX-ACCESS  not-accessible
    STATUS      current
    DESCRIPTION "Contains the settings for traffic shaper of each port."
    ::= { trafficShaperMgt  1 }

trafficShaperPortEntry   OBJECT-TYPE
    SYNTAX      TrafficShaperPortEntry
    MAX-ACCESS  not-accessible
    STATUS      current
    DESCRIPTION "A conceptual row in the trafficShaperPort table."
    INDEX { trafficShaperPortIndex  }
    ::= { trafficShaperPortTable   1 }

TrafficShaperPortEntry::= SEQUENCE
{
    trafficShaperPortIndex                 INTEGER,
    trafficShaperPortOutputStatus          EnabledStatus,
    trafficShaperPortOutputRate            Integer32,
    trafficShaperPortOutputBurstSize       INTEGER
}

trafficShaperPortIndex      OBJECT-TYPE
    SYNTAX      INTEGER
    MAX-ACCESS  not-accessible
    STATUS      current
    DESCRIPTION "The port number of the port that may specify certain entry in the table
                 which contains traffic shaper information."
    ::= { trafficShaperPortEntry  1 }

trafficShaperPortOutputStatus         OBJECT-TYPE
    SYNTAX     EnabledStatus
    MAX-ACCESS  read-write
    STATUS      current
    DESCRIPTION "Sets enabled(1) to enable output feature of traffic shaper for each port, and
                 sets disabled(2) to disable output feature of traffic shaper for each port."
    ::= { trafficShaperPortEntry 5 }

trafficShaperPortOutputRate      OBJECT-TYPE
    SYNTAX      Integer32
    MAX-ACCESS  read-write
    STATUS      current
    DESCRIPTION "Specifies the output rate of traffic shaper for each port.
                 This default value is dynamically determined based on the corresponding
                 value of traffic shaper rate. Setting '0' means that a port uses the system
                 default value as output burst size."
    ::= { trafficShaperPortEntry 6 }

trafficShaperPortOutputBurstSize      OBJECT-TYPE
    SYNTAX      INTEGER
    MAX-ACCESS  read-write
    STATUS      current
    DESCRIPTION "Specifies the output burst size of traffic shaper for each port.
                 Setting '0' means that a port uses the system default value as output burst size."
    ::= { trafficShaperPortEntry 7 }

--
-- trafficShaperPortQueueTable
--

trafficShaperPortQueueTable   OBJECT-TYPE
    SYNTAX      SEQUENCE OF TrafficShaperPortQueueEntry
    MAX-ACCESS  not-accessible
    STATUS      current
    DESCRIPTION "Contains the settings for traffic shaper of queues of each port."
    ::= { trafficShaperMgt  2 }

trafficShaperPortQueueEntry   OBJECT-TYPE
    SYNTAX      TrafficShaperPortQueueEntry
    MAX-ACCESS  not-accessible
    STATUS      current
    DESCRIPTION "A conceptual row in the trafficShaperPortQueue table."
    INDEX { trafficShaperPortQueuePortIndex, trafficShaperPortQueueId }
    ::= { trafficShaperPortQueueTable   1 }

TrafficShaperPortQueueEntry::= SEQUENCE
{
    trafficShaperPortQueuePortIndex             INTEGER,
    trafficShaperPortQueueId                    INTEGER,
    trafficShaperPortQueueOutputStatus          EnabledStatus,
    trafficShaperPortQueueOutputRate            Integer32,
    trafficShaperPortQueueOutputBurstSize       INTEGER
}

trafficShaperPortQueuePortIndex      OBJECT-TYPE
    SYNTAX      INTEGER
    MAX-ACCESS  not-accessible
    STATUS      current
    DESCRIPTION "The port number of the port that may specify certain entry in the table
                 which contains traffic shaper information."
    ::= { trafficShaperPortQueueEntry  1 }

trafficShaperPortQueueId      OBJECT-TYPE
    SYNTAX      INTEGER
    MAX-ACCESS  not-accessible
    STATUS      current
    DESCRIPTION "Specifies the queue ID of a port."
    ::= { trafficShaperPortQueueEntry 2 }

trafficShaperPortQueueOutputStatus         OBJECT-TYPE
    SYNTAX     EnabledStatus
    MAX-ACCESS  read-write
    STATUS      current
    DESCRIPTION "Sets enabled(1) to enable output feature of traffic shaper for each queue of a port, and
                 sets disabled(2) to disable output feature of traffic shaper for each queue of a port."
    ::= { trafficShaperPortQueueEntry 6 }

trafficShaperPortQueueOutputRate      OBJECT-TYPE
    SYNTAX      Integer32
    MAX-ACCESS  read-write
    STATUS      current
    DESCRIPTION "Specifies the output rate of traffic shaper for each queue of a port.
                 Setting '0' means that a port uses the system default value as output rate."
    ::= { trafficShaperPortQueueEntry 7 }

trafficShaperPortQueueOutputBurstSize      OBJECT-TYPE
    SYNTAX      INTEGER
    MAX-ACCESS  read-write
    STATUS      current
    DESCRIPTION "Specifies the output burst size of traffic shaper for each queue of a port.
                 This default value is dynamically determined based on the corresponding
                 value of traffic shaper rate. Setting '0' means that a port uses the system
                 default value as input burst size."
    ::= { trafficShaperPortQueueEntry 8 }

--
-- securityMgt
--

-- Management for security, e.g. user security and port security.

privateVlanMgt      OBJECT IDENTIFIER ::= { securityMgt 1 }
portSecurityMgt     OBJECT IDENTIFIER ::= { securityMgt 2 }
packetFilterUnitMgt OBJECT IDENTIFIER ::= { securityMgt 3 }
radiusMgt           OBJECT IDENTIFIER ::= { securityMgt 4 }
tacacsMgt           OBJECT IDENTIFIER ::= { securityMgt 5 }
sshMgt              OBJECT IDENTIFIER ::= { securityMgt 6 }
aclMgt              OBJECT IDENTIFIER ::= { securityMgt 7 }
bcastFilterMgt      OBJECT IDENTIFIER ::= { securityMgt 8 }
ipFilterMgt         OBJECT IDENTIFIER ::= { securityMgt 9 }
userAuthMgt         OBJECT IDENTIFIER ::= { securityMgt 10 }
dot1xMgt            OBJECT IDENTIFIER ::= { securityMgt 11 }
aaaMgt              OBJECT IDENTIFIER ::= { securityMgt 12 }
networkAccessMgt    OBJECT IDENTIFIER ::= { securityMgt 13 }
macAuthMgt          OBJECT IDENTIFIER ::= { securityMgt 14 }
webAuthMgt          OBJECT IDENTIFIER ::= { securityMgt 15 }


--
-- PrivateVlanMgt
--

-- Management for Private VLAN.
-- SYS_CPNT_PORT_TRAFFIC_SEGMENTATION (use SWCTRL API) start

privateVlanStatus OBJECT-TYPE
        SYNTAX      EnabledStatus
        MAX-ACCESS  read-write
        STATUS      current
        DESCRIPTION "This controls whether private VLAN is enabled."
        ::= { privateVlanMgt 1 }

privateVlanUplinkPorts OBJECT-TYPE
        SYNTAX      PortList
        MAX-ACCESS  read-write
        STATUS      current
        DESCRIPTION "This is the list of uplink ports for private VLAN.
                    They should not overlap with privateVlanDownlinkPorts.
                    0 will be displayed if the privateVlanStatus is disabled.
                    You must enable the privateVlanStatus before setting this variable."
        ::= { privateVlanMgt 2 }

privateVlanDownlinkPorts OBJECT-TYPE
        SYNTAX      PortList
        MAX-ACCESS  read-write
        STATUS      current
        DESCRIPTION "This is the list of downlink ports for private VLAN.
                    They should not overlap with privateVlanUplinkPorts.
                    Multiple port setting is permitted.
                    0 will be displayed if the privateVlanStatus is disabled.
                    You must enable the privateVlanStatus before setting this variable."
        ::= { privateVlanMgt 3 }

privateVlanIsValid OBJECT-TYPE
        SYNTAX      INTEGER
                    {
                        valid(1),
                        invalid(2)
                    }
        MAX-ACCESS  read-only
        STATUS      current
        DESCRIPTION "Indicates whether the private VLAN is valid or not.
                    The private VLAN is valid only when both the uplink and downlink
                    port list are set. This variable will become invalid(2)
                    if you disable the privateVlanStatus."
        ::= { privateVlanMgt 7 }

-- SYS_CPNT_PORT_TRAFFIC_SEGMENTATION (use SWCTRL API) end

-- SYS_CPNT_COMMUNITY_PRIVATE_VLAN (use PVLAN_MGR API) start

privateVlanVlanTable OBJECT-TYPE
        SYNTAX      SEQUENCE OF PrivateVlanVlanEntry
        MAX-ACCESS  not-accessible
        STATUS      current
        DESCRIPTION   "A table containing private VLAN information on the
                       VLANs which currently exist."
        ::= { privateVlanMgt 4 }

privateVlanVlanEntry OBJECT-TYPE
        SYNTAX      PrivateVlanVlanEntry
        MAX-ACCESS  not-accessible
        STATUS      current
        DESCRIPTION  "A conceptual row containing the private VLAN
                      information on the VLANs for a particular management
                      domain."
        INDEX       { privateVlanVlanIndex }
        ::= { privateVlanVlanTable 1 }

PrivateVlanVlanEntry ::= SEQUENCE
{
   privateVlanVlanIndex             Integer32,
   privateVlanVlanType              INTEGER,
   privateVlanAssoicatedPrimaryVlan Integer32
}

privateVlanVlanIndex OBJECT-TYPE
         SYNTAX      Integer32(1..4094)
         MAX-ACCESS  not-accessible
         STATUS      current
         DESCRIPTION "The VLAN ID of this private VLAN."
         ::= { privateVlanVlanEntry 1 }

privateVlanVlanType OBJECT-TYPE
         SYNTAX     INTEGER
                    {
                     invalid(1),
                     primary(2),
                     isolated(3),
                     community(4)
                     }
         MAX-ACCESS read-create
         STATUS     current
         DESCRIPTION "The VLAN type as defined for Private VLAN feature.
                      Set the value to invalid(1) to destroy an entry. Set
                      other values to create an entry. If an index
                      already exists, set others to modifiy it. Note that a VLAN's
                      private VLAN type cannot be changed once it has
                      any port members."
         ::= { privateVlanVlanEntry 2 }

privateVlanAssoicatedPrimaryVlan OBJECT-TYPE
         SYNTAX      Integer32(0..4094)
         MAX-ACCESS  read-create
         STATUS      current
         DESCRIPTION
            "The VLAN ID of the associated primary VLAN used for
            the private VLAN feature if privateVlanVlanType has the
            value of isolated(3), community(4). If privateVlanVlanType
            has the value of primary(2), then this object has the value of 0.

            Note that one isolated VLAN can only be associated
            with one unique primary VLAN. One primary VLAN can only
            be associated with one isolated VLAN.

            One primary VLAN can be associated with multiple community VLANs;
            one community VLAN can only be associated with one unique primary VLAN."
         ::= { privateVlanVlanEntry 3 }


--
-- Table for configuring secondary VLAN on private ports
--

privateVlanPrivatePortTable OBJECT-TYPE
        SYNTAX      SEQUENCE OF PrivateVlanPrivatePortEntry
        MAX-ACCESS  not-accessible
        STATUS      current
        DESCRIPTION
             "A table containing information on the configuration of
              secondary VLANs on the device ports."
        ::= { privateVlanMgt 5 }

privateVlanPrivatePortEntry OBJECT-TYPE
        SYNTAX      PrivateVlanPrivatePortEntry
        MAX-ACCESS  not-accessible
        STATUS      current
        DESCRIPTION
            "A conceptual row containing information of the
            configuration of secondary VLANs for each port. An entry
            is created by the managed system for each interface which
            can be configured as a private port for Private VLAN
            feature."
        INDEX      { privateVlanPrivatePortIfIndex }
        ::= { privateVlanPrivatePortTable 1 }

PrivateVlanPrivatePortEntry ::= SEQUENCE
{
     privateVlanPrivatePortIfIndex        Integer32,
     privateVlanPrivatePortSecondaryVlan  Integer32
}

privateVlanPrivatePortIfIndex OBJECT-TYPE
        SYNTAX      Integer32
        MAX-ACCESS  not-accessible
        STATUS      current
        DESCRIPTION "This is defined as the ifIndex."
        ::= { privateVlanPrivatePortEntry 1 }

privateVlanPrivatePortSecondaryVlan OBJECT-TYPE
        SYNTAX      Integer32(0..4094)
        MAX-ACCESS  read-write
        STATUS      current
        DESCRIPTION
              "The VLAN ID of the secondary VLAN configured on this
              private port. A private port is a port that allows
              ingress traffic of the secondary VLAN as well as
              egress traffic of its associated primary VLAN, but
              blocks the egress traffic of the isolated VLAN while
              allowing the egress traffic of the community
              or twoWayCommunity VLAN depending on the type of the
              secondary VLAN.

              Note that a port can join a secondary VLAN only after
              this secondary VLAN has been associated with a primary
              VLAN, i.e., the cpvlanVlanAssociatedPrimaryVlan has a
              non-zero value. The default value of 0 for this object
              means this port has not yet joined a secondary VLAN."
        DEFVAL     { 0 }
        ::= { privateVlanPrivatePortEntry 2 }

--
-- Table for remapping secondary VLAN to primary VLAN on promiscuous
-- ports for Private VLAN feature
--

privateVlanPromPortTable OBJECT-TYPE
        SYNTAX     SEQUENCE OF PrivateVlanPromPortEntry
        MAX-ACCESS not-accessible
        STATUS     current
        DESCRIPTION "A table containing secondary VLAN to primary VLAN remapping
                    information on ports of the device."
        ::= { privateVlanMgt 6 }

privateVlanPromPortEntry OBJECT-TYPE
        SYNTAX      PrivateVlanPromPortEntry
        MAX-ACCESS  not-accessible
        STATUS      current
        DESCRIPTION "A conceptual row containing secondary VLAN to primary
                    VLAN remapping information for each port.
                    An entry is created by the managed system for each interface
                     which can be configured as a promiscuous port for the
                     private VLAN feature."
        INDEX      { privateVlanPromPortIfIndex }
        ::= { privateVlanPromPortTable 1 }

PrivateVlanPromPortEntry ::= SEQUENCE
{
    privateVlanPromPortIfIndex          Integer32,
    privateVlanPromPortPrimaryVlanId    Integer32,
    privateVlanPromPortSecondaryRemap   OCTET STRING,
    privateVlanPromPortSecondaryRemap2k OCTET STRING,
    privateVlanPromPortSecondaryRemap3k OCTET STRING,
    privateVlanPromPortSecondaryRemap4k OCTET STRING
}

privateVlanPromPortIfIndex OBJECT-TYPE
    SYNTAX       Integer32
    MAX-ACCESS   not-accessible
    STATUS       current
    DESCRIPTION  "This is defined as ifIndex."
    ::= { privateVlanPromPortEntry 1 }

privateVlanPromPortPrimaryVlanId OBJECT-TYPE
    SYNTAX      Integer32(0..4094)
    MAX-ACCESS  read-write
    STATUS      current
    DESCRIPTION "The primary VLAN ID of the promiscous port."
    ::= { privateVlanPromPortEntry 2 }

privateVlanPromPortSecondaryRemap OBJECT-TYPE
    SYNTAX     OCTET STRING (SIZE (0..128))
    MAX-ACCESS read-only
    STATUS     current
    DESCRIPTION
            "A string of octets containing one bit per VLAN in the
            management domain on this port. The first octet
            corresponds to VLANs with VlanIndexOrZero values of 0
            through 7; the second octet to VLANs 8 through 15; etc.
            The most significant bit of each octet corresponds to
            the lowest value VlanIndexOrZero in that octet.

            Note that if the length of this string is less than
            128 octets, any 'missing' octets are assumed to contain
            the value zero. An NMS may omit any zero-valued octets
            from the end of this string in order to reduce SetPDU
            size, and the agent may also omit zero-valued trailing
            octets, to reduce the size of GetResponse PDUs."
    ::= { privateVlanPromPortEntry 3 }

privateVlanPromPortSecondaryRemap2k OBJECT-TYPE
    SYNTAX     OCTET STRING (SIZE (0..128))
    MAX-ACCESS read-only
    STATUS     current
    DESCRIPTION
            "A string of octets containing one bit per VLAN for
            VLANs with VlanIndexOrZero values of 1024 through 2047
            in the management domain on this port. The first octet
            corresponds to VLANs with VlanIndexOrZero values of 1024
            through 1031; the second octet to VLANs 1032 through
            1039; etc. The most significant bit of each octet
            corresponds to the lowest value VlanIndexOrZero in
            that octet.

            Note that if the length of this string is less than
            128 octets, any 'missing' octets are assumed to contain
            the value zero. An NMS may omit any zero-valued octets
            from the end of this string in order to reduce SetPDU
            size, and the agent may also omit zero-valued trailing
            octets, to reduce the size of GetResponse PDUs.

            This object is only instantiated on devices which support
            the range of VlanIndexOrZero up to 4095."
    ::= { privateVlanPromPortEntry 4 }

privateVlanPromPortSecondaryRemap3k OBJECT-TYPE
    SYNTAX     OCTET STRING (SIZE (0..128))
    MAX-ACCESS read-only
    STATUS     current
    DESCRIPTION
            "A string of octets containing one bit per VLAN for
            VLANs with VlanIndexOrZero values of 2048 through 3071
            in the management domain on this port. The first octet
            corresponds to VLANs with VlanIndexOrZero values of 2048
            through 2055; the second octet to VLANs 2056 through
            2063; etc. The most significant bit of each octet
            corresponds to the lowest value VlanIndexOrZero in
            that octet.

            Note that if the length of this string is less than
            128 octets, any 'missing' octets are assumed to contain
            the value zero. An NMS may omit any zero-valued octets
            from the end of this string in order to reduce SetPDU
            size, and the agent may also omit zero-valued trailing
            octets, to reduce the size of GetResponse PDUs.

            This object is only instantiated on devices which support
            the range of VlanIndexOrZero up to 4095."
    ::= { privateVlanPromPortEntry 5 }

privateVlanPromPortSecondaryRemap4k OBJECT-TYPE
    SYNTAX     OCTET STRING (SIZE (0..128))
    MAX-ACCESS read-only
    STATUS     current
    DESCRIPTION
            "A string of octets containing one bit per VLAN for
            VLANs with VlanIndexOrZero values of 3072 through 4095
            in the management domain on this port. The first octet
            corresponds to VLANs with VlanIndexOrZero values of 3072
            through 3079; the second octet to VLANs 3080 through
            3087; etc. The most significant bit of each octet
            corresponds to the lowest value VlanIndexOrZero in
            that octet.

            Note that if the length of this string is less than
            128 octets, any 'missing' octets are assumed to contain
            the value zero. An NMS may omit any zero-valued octets
            from the end of this string in order to reduce SetPDU
            size, and the agent may also omit zero-valued trailing
            octets, to reduce the size of GetResponse PDUs.

            This object is only instantiated on devices which support
            the range of VlanIndexOrZero up to 4095."
    ::= { privateVlanPromPortEntry 6 }
-- SYS_CPNT_COMMUNITY_PRIVATE_VLAN (use PVLAN_MGR API) end

-- PortSecurityMgt

-- Management for Port Security. A secure port only allows
-- secure MAC addresses to come in.



portSecPortTable OBJECT-TYPE
        SYNTAX      SEQUENCE OF PortSecPortEntry
        MAX-ACCESS  not-accessible
        STATUS      current
        DESCRIPTION "The port security (MAC binding) Table."
        ::= { portSecurityMgt 1 }

portSecPortEntry OBJECT-TYPE
        SYNTAX      PortSecPortEntry
        MAX-ACCESS  not-accessible
        STATUS      current
        DESCRIPTION "The entry of portSecPortTable."
        INDEX       { portSecPortIndex }
        ::= { portSecPortTable 1 }

PortSecPortEntry ::= SEQUENCE
{
      portSecPortIndex          Integer32,
      portSecPortStatus         EnabledStatus,
      portSecAction             INTEGER,
      portSecMaxMacCount        Integer32,
      portSecShutdownInterval   Integer32,
      portSecLearningStatus     EnabledStatus
}

portSecPortIndex OBJECT-TYPE
        SYNTAX      Integer32
        MAX-ACCESS  not-accessible
        STATUS      current
        DESCRIPTION "The port and the trunk (excluding trunk members) interface of
                     the portTable. The interface identified by a particular value
                     of this index is the same interface as identified by the same
                     value of ifIndex in the IF-MIB."
        ::= { portSecPortEntry 1 }

portSecPortStatus OBJECT-TYPE
        SYNTAX      EnabledStatus
        MAX-ACCESS  read-write
        STATUS      current
        DESCRIPTION "Set enabled(1) to enable port security and set disabled(2) to
                     disable port security."
        ::= { portSecPortEntry 2  }

portSecAction OBJECT-TYPE
        SYNTAX        INTEGER
                      {
                        none(1),
                        trap(2),
                        shutdown(3),
                        trapAndShutdown(4)
                      }
        MAX-ACCESS    read-write
        STATUS        current
        DESCRIPTION  "The corresponding actions that will take place when a
                      port is under intrusion, when this variable is set to
                      none(1), no action will be performed, when this variable is
                      set to trap(2), a swPortSecurityTrap trap will be sent,
                      when this variable is set to shutdown(3), the port will
                      shutdown, when this variable is set to
                      trapAndShutdown(4), a swPortSecurityTrap will be sent
                      and the port will shutdown."
        ::= { portSecPortEntry 3  }

portSecMaxMacCount OBJECT-TYPE
        SYNTAX       Integer32(0..1024)
        MAX-ACCESS   read-write
        STATUS       current
        DESCRIPTION  "The maximun number of MAC addresses that will be learned and locked.
                      When we change the value of this variable, if the
                      portSecPortStatus is enabled, we will discard all secure MAC
                      and begin to learn again, until the number of MAC has reached
                      this value, and only the secure MAC addresses can enter
                      this port. If the portSecPortStatus is disabled, we will begin
                      to learn the MAC, and auto enabled the portSecPortStatus when
                      the MAC has reached this value."
        ::= { portSecPortEntry 4 }

portSecShutdownInterval OBJECT-TYPE
        SYNTAX       Integer32(0..1440)
        MAX-ACCESS   read-write
        STATUS       current
        DESCRIPTION  "Set the shutdown interval if port security violation occurs.
                      After this interval, the software enables the port automatically.
                      The range is between 1 and 1440 minutes. If this value is not specified,
                      the default is disable forever by default (0)."
        DEFVAL       { 0 }
        ::= { portSecPortEntry 5 }

portSecLearningStatus OBJECT-TYPE
        SYNTAX       EnabledStatus
        MAX-ACCESS   read-write
        STATUS       current

        DESCRIPTION  " Set enabled(1) to discard all secured MAC addresses and to learn
                new addresses. After the number of MAC addresses reaches portSecMaxMacCount,
                only the secured MAC adddresses can transmit packets through this port.
                Set disabled(2) to stop the autolearn process, and then only the secure
                MAC addresses can transmit packets through this port."

        DEFVAL       { disabled }
        ::= { portSecPortEntry 6 }

portSecMacTable OBJECT-TYPE
        SYNTAX      SEQUENCE OF PortSecMacEntry
        MAX-ACCESS  not-accessible
        STATUS      current
        DESCRIPTION "The Port Security(MAC address binding) Table"
        ::= { portSecurityMgt 2 }

portSecMacEntry OBJECT-TYPE
        SYNTAX      PortSecMacEntry
        MAX-ACCESS  not-accessible
        STATUS      current
        DESCRIPTION "The entry of portSecMacTable"
        INDEX       { portSecMacPortIndex,
                      portSecMacVlanIndex,
                      portSecMacAddress }
        ::= { portSecMacTable 1 }

PortSecMacEntry ::= SEQUENCE
{
      portSecMacPortIndex      Integer32,
      portSecMacVlanIndex      Integer32,
      portSecMacAddress        OCTET STRING,
      portSecMacStatus         ValidStatus
}

portSecMacPortIndex OBJECT-TYPE
        SYNTAX      Integer32
        MAX-ACCESS  not-accessible
        STATUS      current
        DESCRIPTION "The port and the trunk (excluding trunk members) interface of
                     the portTable. The interface identified by a particular value
                     of this index is the same interface as identified by the same
                     value of ifIndex in the IF-MIB."
        ::= { portSecMacEntry 1 }

portSecMacVlanIndex OBJECT-TYPE
        SYNTAX      Integer32
        MAX-ACCESS  not-accessible
        STATUS      current
        DESCRIPTION "The interface identified by a particular value of
                     this index is the same interface as identified by
                     the same value of dot1qVlanIndex in the Q-BRIDGE-MIB."
        ::= { portSecMacEntry 2 }

portSecMacAddress OBJECT-TYPE
        SYNTAX      OCTET STRING(SIZE(6))
        MAX-ACCESS  not-accessible
        STATUS      current
        DESCRIPTION "Specifies a secure MAC address for the interface and
                     adds additional secure MAC addresses up to the maximum
                     value configured."
        ::= { portSecMacEntry 3 }

portSecMacStatus OBJECT-TYPE
        SYNTAX      ValidStatus
        MAX-ACCESS  read-create
        STATUS      current
        DESCRIPTION "Setting this to valid(1) creates an entry.
                     Setting this to invalid(2) destroys an entry."
        ::= { portSecMacEntry 4 }

portSecAgingStatus OBJECT-TYPE
        SYNTAX      EnabledStatus
        MAX-ACCESS  read-write
        STATUS      current
        DESCRIPTION "Set portSecAgingStatus to valid to age out learned secure
                     address entries for all ports. The default setting
                     is disabled."
        DEFVAL       { disabled }
        ::= { portSecurityMgt 3 }

portSecAutoSaveStatus OBJECT-TYPE
        SYNTAX      EnabledStatus
        MAX-ACCESS  read-write
        STATUS      current
        DESCRIPTION "Use the port security autosave global configuration command
                     to enable the running-configuration autosave function.
                     The default setting is disabled."
        DEFVAL       { disabled }
        ::= { portSecurityMgt 4 }

portSecAutoSaveInterval OBJECT-TYPE
        SYNTAX      Integer32(15..1440)
        MAX-ACCESS  read-write
        STATUS      current
        DESCRIPTION "Use the port security autosave global configuration command
                     to enable the running-configuration autosave function.
                     The range is between 15 and 1440 minutes. The default value is 15."
        DEFVAL       { 15 }
        ::= { portSecurityMgt 5 }

-- packetFilterUnitMgt

-- Management for the Packet Filter Unit (PFU).
-- This filter packets (permits or denies) according
-- the certain properties in the UDP, TCP and IP headers.


pfuRuleTable OBJECT-TYPE
        SYNTAX      SEQUENCE OF PfuRuleEntry
        MAX-ACCESS  not-accessible
        STATUS      current
        DESCRIPTION "Table for Packet Filter Unit rules."
        ::= { packetFilterUnitMgt 1 }

pfuRuleEntry OBJECT-TYPE
        SYNTAX      PfuRuleEntry
        MAX-ACCESS  not-accessible
        STATUS      current
        DESCRIPTION "Entry for Packet Filter Unit rules."
        INDEX       { pfuRuleIndex }
        ::= { pfuRuleTable 1 }

PfuRuleEntry ::= SEQUENCE
{
    pfuRuleIndex          Integer32,
    pfuRuleAction         INTEGER,
    pfuRuleProtocol       Integer32,
    pfuRuleSrcIpAddr      IpAddress,
    pfuRuleSrcIpBitmask   IpAddress,
    pfuRuleSrcPortRange1  Integer32,
    pfuRuleSrcPortRange2  Integer32,
    pfuRuleDstIpAddr      IpAddress,
    pfuRuleDstIpBitmask   IpAddress,
    pfuRuleDstPortRange1  Integer32,
    pfuRuleDstPortRange2  Integer32,
    pfuRuleTcpCode        Integer32,
    pfuRuleTcpCodeBitmask Integer32,
    pfuRuleFragments      EnabledStatus,
    pfuRuleLog            EnabledStatus,
    pfuRuleRowStatus      RowStatus
}

pfuRuleIndex OBJECT-TYPE
    SYNTAX      Integer32 (1..128)
    MAX-ACCESS  not-accessible
    STATUS      current
    DESCRIPTION "The index of a rule. Rules are evaluated in this table based
                 on the index. The index forms a single continguous range.
                 If a rule is deleted, the indexes of all rules after the
                 deleted rule will be decreased by 1. If a rule is inserted,
                 the indexes of all rules after the inserted rule will be
                 increased by 1. When adding to the end of the table, a rule
                 can only be created using the index that follows the highest
                 current index."
    ::= { pfuRuleEntry 1 }

pfuRuleAction OBJECT-TYPE
    SYNTAX      INTEGER
                {
                    permit(1),
                    deny(2)
                }
    MAX-ACCESS  read-create
    STATUS      current
    DESCRIPTION "Whether to permit or deny a matching packet."
    DEFVAL      { permit }
    ::= { pfuRuleEntry 2 }

pfuRuleProtocol OBJECT-TYPE
    SYNTAX      Integer32 (0..256)
    MAX-ACCESS  read-create
    STATUS      current
    DESCRIPTION "IP protocol number. pfuRuleProtocol=256 means 'any'.
                 6 means TCP. 17 means UDP."
    DEFVAL      { 256 }
    ::= { pfuRuleEntry 3 }

pfuRuleSrcIpAddr OBJECT-TYPE
    SYNTAX      IpAddress
    MAX-ACCESS  read-create
    STATUS      current
    DESCRIPTION "Source IP address. The default value is
                '00000000'h, that is 0.0.0.0."
    DEFVAL      { '00000000'h }
    ::= { pfuRuleEntry 4 }

pfuRuleSrcIpBitmask OBJECT-TYPE
    SYNTAX      IpAddress
    MAX-ACCESS  read-create
    STATUS      current
    DESCRIPTION "Source IP bitmask. The default value is
                '00000000'h, that is 0.0.0.0."
    DEFVAL      { '00000000'h }
    ::= { pfuRuleEntry 5 }

pfuRuleSrcPortRange1 OBJECT-TYPE
    SYNTAX      Integer32 (0..65536)
    MAX-ACCESS  read-create
    STATUS      current
    DESCRIPTION "Source port of TCP or UDP. This is expressed as a range
                 specified by two boundary values pfuRuleSrcPortRange1
                 and pfuRuleSrcPortRange2. Either of these variables may
                 be used as the lower or upper bound. In order to specify
                 'any', set both of these variables to 65536."
    DEFVAL      { 65536 }
    ::= { pfuRuleEntry 6 }

pfuRuleSrcPortRange2 OBJECT-TYPE
    SYNTAX      Integer32 (0..65536)
    MAX-ACCESS  read-create
    STATUS      current
    DESCRIPTION "Source port of TCP or UDP. This is expressed as a range
                 specified by two boundary values pfuRuleSrcPortRange1
                 and pfuRuleSrcPortRange2. Either of these variables may
                 be used as the lower or upper bound. In order to specify
                 'any', set both of these variables to 65536."
    DEFVAL      { 65536 }
    ::= { pfuRuleEntry 7 }

pfuRuleDstIpAddr OBJECT-TYPE
    SYNTAX      IpAddress
    MAX-ACCESS  read-create
    STATUS      current
    DESCRIPTION "Source IP address. The default value is
                '00000000'h, that is 0.0.0.0."
    DEFVAL      { '00000000'h }
    ::= { pfuRuleEntry 8 }

pfuRuleDstIpBitmask OBJECT-TYPE
    SYNTAX      IpAddress
    MAX-ACCESS  read-create
    STATUS      current
    DESCRIPTION "Source IP bitmask. The default value is
                '00000000'h, that is 0.0.0.0."
    DEFVAL      { '00000000'h }
    ::= { pfuRuleEntry 9 }

pfuRuleDstPortRange1 OBJECT-TYPE
    SYNTAX      Integer32 (0..65536)
    MAX-ACCESS  read-create
    STATUS      current
    DESCRIPTION "TCP or UDP destination port. This is expressed as a range
                 specified by two boundary values pfuRuleDstPortRange1 and
                 pfuRuleDstPortRange2. Either of these variables may be used
                 as the lower or upper bound. In order to specify 'any', set
                 both of these variables to 65536."
    DEFVAL      { 65536 }
    ::= { pfuRuleEntry 10 }

pfuRuleDstPortRange2 OBJECT-TYPE
    SYNTAX      Integer32 (0..65536)
    MAX-ACCESS  read-create
    STATUS      current
    DESCRIPTION "TCP or UDP destination port. This is expressed as a range
                 specified by two boundary values pfuRuleDstPortRange1 and
                 pfuRuleDstPortRange2. Either of these variables may be used
                 as the lower or upper bound. In order to specify 'any', set
                 both of these variables to 65536."
    DEFVAL      { 65536 }
    ::= { pfuRuleEntry 11 }

pfuRuleTcpCode OBJECT-TYPE
    SYNTAX      Integer32 (0..63)
    MAX-ACCESS  read-create
    STATUS      current
    DESCRIPTION "TCP control code. Combination of six bits. The values
                 are: (1) FIN - finish, (2) SYN - synchronise
                 (start a connection), (4) RST - reset, (8) PSH - push,
                 (16) ACK - acknowledgment, (32) URG - urgent pointer."
    DEFVAL      { 0 }
    ::= { pfuRuleEntry 12 }

pfuRuleTcpCodeBitmask OBJECT-TYPE
    SYNTAX      Integer32 (0..63)
    MAX-ACCESS  read-create
    STATUS      current
    DESCRIPTION "TCP control bitmask."
    DEFVAL      { 0 }
    ::= { pfuRuleEntry 13 }

pfuRuleFragments OBJECT-TYPE
    SYNTAX      EnabledStatus
    MAX-ACCESS  read-create
    STATUS      current
    DESCRIPTION "If set, the rule will only match packets with the More Fragments
                 (MF) bit set or with a fragment offset greater than zero. If not
                 set, the rule will match both fragment and non-fragment packets."
    DEFVAL      { disabled }
    ::= { pfuRuleEntry 14 }

pfuRuleLog OBJECT-TYPE
    SYNTAX      EnabledStatus
    MAX-ACCESS  read-create
    STATUS      current
    DESCRIPTION "Whether to log or not."
    DEFVAL      { disabled }
    ::= { pfuRuleEntry 15 }

pfuRuleRowStatus OBJECT-TYPE
    SYNTAX      RowStatus
    MAX-ACCESS  read-create
    STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { pfuRuleEntry 16 }

pfuNextAvailable OBJECT-TYPE
    SYNTAX      Integer32 (0..128)
    MAX-ACCESS  read-only
    STATUS      current
    DESCRIPTION "The next available index for row creation.
                 If the table is full, this variable returns 0."
    ::= { packetFilterUnitMgt 2 }

pfuInsert OBJECT-TYPE
    SYNTAX      Integer32 (0..128)
    MAX-ACCESS  read-write
    STATUS      current
    DESCRIPTION "To insert a rule at a specified index, set this variable to an
                 index of the new rule (1..128). The index of the existing rules
                 at the target position and beyond will be increased by 1. To
                 append a rule at the end, set this variable to the maximum
                 existing index plus 1. The new rule will have the specified
                 index and its row status will be notInService(2). The insertion
                 will fails and return error if the table is already full.
                 0 will always be obtained when reading this variable."
    ::= { packetFilterUnitMgt 3 }

--
-- radiusMgt
-- (the newly radiusMgt in ES3526v-60)

-- Management for Remote Authentication Dial-In User Service (RADIUS).
--SYS_ADPT_MAX_NBR_OF_RADIUS_SERVERS=1: single server
--SYS_ADPT_MAX_NBR_OF_RADIUS_SERVERS>1: multiple server
--
--radiusServerGlobalAuthPort OBJECT-TYPE
--        SYNTAX      Integer32 (1..65535)
--        MAX-ACCESS  read-write
--        STATUS      current
--        DESCRIPTION "Aauthentication port number for RADIUS server.
--                     When specified radius server do not set
--               aauthentication port number, this value is used."
--        ::= { radiusMgt 1 }
--
--radiusServerGlobalAcctPort OBJECT-TYPE
--        SYNTAX      Integer32 (1..65535)
--        MAX-ACCESS  read-write
--        STATUS      current
--        DESCRIPTION "Accounting port number of RADIUS server.
--                    When specified radius server do not set
--               accounting port number, this value is used."
--        ::= { radiusMgt 2 }
--
--radiusServerGlobalKey OBJECT-TYPE
--        SYNTAX      DisplayString(SIZE(0..48))
--        MAX-ACCESS  read-write
--        STATUS      current
--        DESCRIPTION "Key for RADIUS. This variable can only be written.
--                     When this variable is read, it always returns a
--                     zero-length string.
--                     When specified radius server do not set
--               key, this this value is used."
--        ::= { radiusMgt 3 }
--
--radiusServerGlobalRetransmit OBJECT-TYPE
--        SYNTAX      INTEGER (0..100)
--        MAX-ACCESS  read-write
--        STATUS      current
--        DESCRIPTION "Maximum number of retransmissions for RADIUS.
--                     When specified radius server do not set
--               maximum number of retransmissions, this value is used."
--        ::= { radiusMgt 4 }
--
--radiusServerGlobalTimeout OBJECT-TYPE
--        SYNTAX      INTEGER (1..1000)
--        MAX-ACCESS  read-write
--        STATUS      current
--        DESCRIPTION "Timeout for RADIUS.
--                     When specified radius server do not set
--               timeout, this value is used."
--        ::= { radiusMgt 5 }
--
--
--radiusServerTable OBJECT-TYPE
--        SYNTAX      SEQUENCE OF RadiusServerEntry
--        MAX-ACCESS  not-accessible
--       STATUS      current
--        DESCRIPTION "The table for RADIUS server."
--        ::= { radiusMgt 7 }
--
--radiusServerEntry OBJECT-TYPE
--        SYNTAX      RadiusServerEntry
--        MAX-ACCESS  not-accessible
--        STATUS      current
--        DESCRIPTION "The conceptual row for radiusServerTable."
--        INDEX       { radiusServerIndex }
--        ::= { radiusServerTable 1 }
--
--RadiusServerEntry ::= SEQUENCE
--{
--   radiusServerIndex                  Integer32,
--   radiusServerAddress                IpAddress,
--   radiusServerAuthPortNumber             Integer32,
--   radiusServerAcctPortNumber         Integer32,
--   radiusServerKey                DisplayString,
--   radiusServerRetransmit         Integer32,
--   radiusServerTimeout                Integer32,
--   radiusServerStatus                 ValidStatus
--}
--
--radiusServerIndex OBJECT-TYPE
--        SYNTAX      Integer32
--        MAX-ACCESS  not-accessible
--        STATUS      current
--        DESCRIPTION "The RADIUS  server index in the table."
--        ::= { radiusServerEntry 1 }
--
-- radiusServerAddress OBJECT-TYPE
--        SYNTAX      IpAddress
--        MAX-ACCESS  read-create
--        STATUS      current
--        DESCRIPTION "IP address of a RADIUS server."
--        ::= { radiusServerEntry 2 }
--
--radiusServerAuthPortNumber OBJECT-TYPE
--        SYNTAX      Integer32 (1..65535)
--        MAX-ACCESS  read-create
--        STATUS      current
--        DESCRIPTION "Authentication port number of RADIUS server."
--        ::= { radiusServerEntry 3 }
--
--radiusServerAcctPortNumber OBJECT-TYPE
--        SYNTAX      Integer32 (1..65535)
--        MAX-ACCESS  read-create
--        STATUS      current
--        DESCRIPTION "Accounting port number of RADIUS server."
--        ::= { radiusServerEntry 4 }
--
--
--radiusServerKey OBJECT-TYPE
--        SYNTAX      DisplayString(SIZE(0..48))
--        MAX-ACCESS  read-write
--        STATUS      current
--        DESCRIPTION "Key for RADIUS. This variable can only be written.
--                     When this variable is read, it always returns a
--                     zero-length string."
--        ::= { radiusServerEntry 5 }
--
--radiusServerRetransmit OBJECT-TYPE
--        SYNTAX      Integer32 (0..100)
--        MAX-ACCESS  read-write
--        STATUS      current
--        DESCRIPTION "Timeout for RADIUS."
--        ::= { radiusServerEntry 6 }
--
--radiusServerTimeout OBJECT-TYPE
--        SYNTAX      Integer32(1..1000)
--        MAX-ACCESS  read-write
--        STATUS      current
--        DESCRIPTION "Timeout for RADIUS."
--        ::= { radiusServerEntry 7 }
--
--radiusServerStatus OBJECT-TYPE
--        SYNTAX      ValidStatus
--        MAX-ACCESS  read-create
--        STATUS      current
--        DESCRIPTION "Setting this to valid(1) creates an entry.
--                     Setting this to invalid(2) destroys an entry."
--        ::= { radiusServerEntry 8 }
--
--

radiusServerAddress OBJECT-TYPE
        SYNTAX      IpAddress
        MAX-ACCESS  read-write
        STATUS      current
        DESCRIPTION "IP address of RADIUS server."
        ::= { radiusMgt 1 }

radiusServerPortNumber OBJECT-TYPE
        SYNTAX      Integer32 (1..65535)
        MAX-ACCESS  read-write
        STATUS      current
        DESCRIPTION "IP port number of RADIUS server."
        ::= { radiusMgt 2 }

radiusServerKey OBJECT-TYPE
        SYNTAX      DisplayString(SIZE(0..48))
        MAX-ACCESS  read-write
        STATUS      current
        DESCRIPTION "Key for RADIUS. This variable can only be set.
                     When this variable is read, it always returns a
                     zero-length string."
        ::= { radiusMgt 3 }

radiusServerRetransmit OBJECT-TYPE
        SYNTAX      Integer32 (1..30)
        MAX-ACCESS  read-write
        STATUS      current
        DESCRIPTION "Maximum number of retransmissions for RADIUS."
        ::= { radiusMgt 4 }

radiusServerTimeout OBJECT-TYPE
        SYNTAX      Integer32 (1..65535)
        UNITS       "seconds"
        MAX-ACCESS  read-write
        STATUS      current
        DESCRIPTION "Timeout for RADIUS."
        ::= { radiusMgt 5 }

radiusServerHostName OBJECT-TYPE
        SYNTAX      DisplayString(SIZE(0..255))
        MAX-ACCESS  read-write
        STATUS      current
        DESCRIPTION "IP address or DNS of RADIUS server."
        ::= { radiusMgt 6 }

--radiusMultipleServerTable

radiusMultipleServerTable OBJECT-TYPE
        SYNTAX      SEQUENCE OF RadiusMultipleServerEntry
        MAX-ACCESS  not-accessible
        STATUS      current
        DESCRIPTION "The table for multiple RADIUS server."
        ::= { radiusMgt 7 }

radiusMultipleServerEntry OBJECT-TYPE
        SYNTAX      RadiusMultipleServerEntry
        MAX-ACCESS  not-accessible
        STATUS      current
        DESCRIPTION "The conceptual row for radiusMultipleServerTable."
        INDEX       { radiusMultipleServerIndex }
        ::= { radiusMultipleServerTable 1 }

RadiusMultipleServerEntry ::= SEQUENCE
{
   radiusMultipleServerIndex      Integer32,
   radiusMultipleServerAddress    IpAddress,
   radiusMultipleServerPortNumber Integer32,
   radiusMultipleServerKey        DisplayString,
   radiusMultipleServerRetransmit Integer32,
   radiusMultipleServerTimeout    Integer32,
   radiusMultipleServerStatus     ValidStatus
}

radiusMultipleServerIndex OBJECT-TYPE
        SYNTAX      Integer32
        MAX-ACCESS  not-accessible
        STATUS      current
        DESCRIPTION "The RADIUS multiple server index."
        ::= { radiusMultipleServerEntry 1 }

radiusMultipleServerAddress OBJECT-TYPE
        SYNTAX      IpAddress
        MAX-ACCESS  read-create
        STATUS      current
        DESCRIPTION "IP address of a multiple RADIUS server."
        ::= { radiusMultipleServerEntry 2 }

radiusMultipleServerPortNumber OBJECT-TYPE
        SYNTAX      Integer32 (1..65535)
        MAX-ACCESS  read-create
        STATUS      current
        DESCRIPTION "IP port number of a multiple RADIUS server."
        ::= { radiusMultipleServerEntry 3 }

radiusMultipleServerKey OBJECT-TYPE
        SYNTAX      DisplayString(SIZE(0..48))
        MAX-ACCESS  read-create
        STATUS      current
        DESCRIPTION "Key for RADIUS. This variable can only be set.
                     When this variable is read, it always returns a
                     zero-length string."
        ::= { radiusMultipleServerEntry 4 }

radiusMultipleServerRetransmit OBJECT-TYPE
        SYNTAX      Integer32 (1..30)
        MAX-ACCESS  read-create
        STATUS      current
        DESCRIPTION "Maximum number of retransmissions for RADIUS."
        ::= { radiusMultipleServerEntry 5 }

radiusMultipleServerTimeout OBJECT-TYPE
        SYNTAX      Integer32 (1..65535)
        UNITS       "seconds"
        MAX-ACCESS  read-create
        STATUS      current
        DESCRIPTION "Timeout for RADIUS."
        ::= { radiusMultipleServerEntry 6 }

radiusMultipleServerStatus OBJECT-TYPE
        SYNTAX      ValidStatus
        MAX-ACCESS  read-create
        STATUS      current
        DESCRIPTION "Setting this to valid(1) creates an entry.
                     Setting this to invalid(2) destroys an entry."
        ::= { radiusMultipleServerEntry 8 }


-- tacacsMgt
-- (The newly tacacsMgt is in ES4548-08)
-- Management for Terminal Access Controller Access Control System plus (TACACS+).
-- Global server setting
--The aaaMethodTable is change to aaaAccountMethodTable in ES4548-08
--tacacsPlusServerGlobalPortNumber OBJECT-TYPE
--        SYNTAX      Integer32 (1..65535)
--        MAX-ACCESS  read-write
--        STATUS      current
--        DESCRIPTION "TCP port number of TACACS+ server.
--                     When specified TACACS+ server do not set
--               TCP port number, this this value is used."
--        ::= { tacacsMgt 2 }
--
--tacacsPlusServerGlobalKey OBJECT-TYPE
--        SYNTAX      DisplayString(SIZE(0..48))
--        MAX-ACCESS  read-write
--        STATUS      current
--        DESCRIPTION  "The encryption key used to encrpt the traffic between client and
--                TACACS+ server. Do not use blank spaces in the string. This variable
--                can only be set. When this variable is read, it always returns a
--                zero-length string.When specified TACACS+ server do not set
--                the encryption key , this this value is used."
--        ::= { tacacsMgt 3 }
--
--tacacsPlusServerTable OBJECT-TYPE
--        SYNTAX      SEQUENCE OF TacacsPlusServerEntry
--        MAX-ACCESS  not-accessible
--        STATUS      current
--        DESCRIPTION "The table for TACACS+ server."
--        ::= { tacacsMgt 4 }
--
--tacacsPlusServerEntry OBJECT-TYPE
--        SYNTAX      TacacsPlusServerEntry
--        MAX-ACCESS  not-accessible
--        STATUS      current
--        DESCRIPTION "The conceptual row for tacacsPlusServerTable."
--        INDEX       { tacacsPlusServerIndex }
--        ::= { tacacsPlusServerTable 1 }
--
--TacacsPlusServerEntry ::= SEQUENCE
--{
--   tacacsPlusServerIndex      Integer32,
--   tacacsPlusServerAddress    IpAddress,
--   tacacsPlusServerPortNumber Integer32,
--   tacacsPlusServerKey          DisplayString,
--   tacacsPlusServerStatus     ValidStatus
--}
--
--tacacsPlusServerIndex OBJECT-TYPE
--        SYNTAX      Integer32
--        MAX-ACCESS  not-accessible
--        STATUS      current
--        DESCRIPTION "TACACS+ server index."
--        ::= { tacacsPlusServerEntry 1 }
--
--tacacsPlusServerAddress OBJECT-TYPE
--        SYNTAX      IpAddress
--        MAX-ACCESS  read-create
--        STATUS      current
--        DESCRIPTION "IP address of a TACACS+ server."
--        ::= { tacacsPlusServerEntry 2 }
--
--tacacsPlusServerPortNumber OBJECT-TYPE
--        SYNTAX      Integer32 (1..65535)
--        MAX-ACCESS  read-create
--        STATUS      current
--        DESCRIPTION "TCP port number of a TACACS+ server."
--        ::= { tacacsPlusServerEntry 3 }
--
--tacacsPlusServerKey OBJECT-TYPE
--        SYNTAX      DisplayString(SIZE(0..48))
--        MAX-ACCESS  read-create
--        STATUS      current
--        DESCRIPTION  "The encryption key used to encrpt the traffic between client and
--                   TACACS+ server. Do not use blank spaces in the string. This
--                   variable can only be set. When this variable is read, it always
--                   returns a zero-length string."
--        ::= { tacacsPlusServerEntry 4 }
--
--tacacsPlusServerStatus OBJECT-TYPE
--        SYNTAX      ValidStatus
--        MAX-ACCESS  read-create
--        STATUS      current
--        DESCRIPTION "Setting this to valid(1) creates an entry.
--                     Setting this to invalid(2) destroys an entry."
--        ::= { tacacsPlusServerEntry 8 }
--
--
--
--
--
--
--
-- tacacsMgt
--

-- Management for Terminal Access Controller Access Control System plus (TACACS+).

tacacsServerAddress OBJECT-TYPE
        SYNTAX      IpAddress
        MAX-ACCESS  read-write
        STATUS      current
        DESCRIPTION "IP address of TACACS server."
        ::= { tacacsMgt 1 }

tacacsServerPortNumber OBJECT-TYPE
        SYNTAX      Integer32 (1..65535)
        MAX-ACCESS  read-write
        STATUS      current
        DESCRIPTION "IP port number of TACACS server."
        ::= { tacacsMgt 2 }

tacacsServerKey OBJECT-TYPE
        SYNTAX      DisplayString(SIZE(0..48))
        MAX-ACCESS  read-write
        STATUS      current
        DESCRIPTION  "The encryption key used to authenticate logon access
                     for the client using TACAS. Do not use blank spaces
                     in the string. This variable can only be set.
                     When this variable is read, it always returns a zero-length string."
        ::= { tacacsMgt 3 }

tacacsServerHostName OBJECT-TYPE
        SYNTAX      DisplayString(SIZE(0..255))
        MAX-ACCESS  read-write
        STATUS      current
        DESCRIPTION "IP address or DNS of TACACS server."
        ::= { tacacsMgt 4 }

--
-- sshMgt
--

-- Management for Secure Shell Configuration

sshServerStatus OBJECT-TYPE
        SYNTAX      EnabledStatus
        MAX-ACCESS  read-write
        STATUS      current
        DESCRIPTION "The status of Secure Shell Server. Set this value to
                     enabled(1) to enable SSH server, set this value to
                     disabled(2) to disable the SSH server."
        ::= { sshMgt 1 }

sshServerMajorVersion  OBJECT-TYPE
        SYNTAX      Integer32
        MAX-ACCESS  read-only
        STATUS      current
        DESCRIPTION "The major version of the SSH Server."
        ::= { sshMgt 2 }

sshServerMinorVersion  OBJECT-TYPE
        SYNTAX      Integer32
        MAX-ACCESS  read-only
        STATUS      current
        DESCRIPTION "The minor version of the SSH Server."
        ::= { sshMgt 3 }

sshTimeout OBJECT-TYPE
        SYNTAX      INTEGER(1..120)
        UNITS       "seconds"
        MAX-ACCESS  read-write
        STATUS      current
        DESCRIPTION "The time interval that the router waits for the SSH
                     client to respond. The range is 1-120."
        ::= { sshMgt 4 }

sshAuthRetries OBJECT-TYPE
        SYNTAX      INTEGER(1..5)
        MAX-ACCESS  read-write
        STATUS      current
        DESCRIPTION "The number of attempts after which the interface is reset.
                     The range is 1-5."
        ::= { sshMgt 5 }

sshConnInfoTable OBJECT-TYPE
        SYNTAX      SEQUENCE OF SshConnInfoEntry
        MAX-ACCESS  not-accessible
        STATUS      current
        DESCRIPTION "The table for Secure Shell Connection."
        ::= { sshMgt 6 }

sshConnInfoEntry OBJECT-TYPE
        SYNTAX      SshConnInfoEntry
        MAX-ACCESS  not-accessible
        STATUS      current
        DESCRIPTION "The conceptual row for sshConnInfoTable."
        INDEX       { sshConnID }
        ::= { sshConnInfoTable 1 }

SshConnInfoEntry ::= SEQUENCE
{
--both sshv1 & sshv2 start
   sshConnID             Integer32,
   sshConnMajorVersion   Integer32,
   sshConnMinorVersion   Integer32,
   sshConnStatus         INTEGER,
--both sshv1 & sshv2 end
--sshv1 only start
   sshConnEncryptionType INTEGER,
--sshv1 only end
--both sshv1 & sshv2 start
   sshConnUserName       DisplayString,
   sshDisconnect         INTEGER,
--both sshv1 & sshv2 end
--sshv2 only start
   sshConnEncryptionTypeStr DisplayString
--sshv2 only end
}

--both sshv1 & sshv2 start
sshConnID OBJECT-TYPE
        SYNTAX      Integer32
        MAX-ACCESS  not-accessible
        STATUS      current
        DESCRIPTION "The connection ID of the Secure Shell Connection."
        ::= { sshConnInfoEntry 1 }

sshConnMajorVersion OBJECT-TYPE
        SYNTAX      Integer32
        MAX-ACCESS  read-only
        STATUS      current
        DESCRIPTION "The SSH major version."
        ::= { sshConnInfoEntry 2 }

sshConnMinorVersion OBJECT-TYPE
        SYNTAX      Integer32
        MAX-ACCESS  read-only
        STATUS      current
        DESCRIPTION "The SSH minor version."
        ::= { sshConnInfoEntry 3 }

sshConnStatus OBJECT-TYPE
        SYNTAX      INTEGER
                    {
                      negotiationStart(1),
                      authenticationStart(2),
                      sessionStart(3)
                    }
        MAX-ACCESS  read-only
        STATUS      current
        DESCRIPTION "The SSH connection State. negotiationStart(1) means the
                     SSH is in its negotiation start state, authenticationStart(2)
                     means the SSH is in authentication start state, sessionStart(3)
                     means the SSH is in session start State."
        ::= { sshConnInfoEntry 5 }

--both sshv1 & sshv2 end
--sshv1 only start
sshConnEncryptionType OBJECT-TYPE
        SYNTAX      INTEGER
                    {
                      none(1),
                      des(2),
                      tribeDes(3)
                    }
        MAX-ACCESS  read-only
        STATUS      current
        DESCRIPTION "The encryption type of the SSH. none(1) means no encryption
                     , des(2) means using DES encryption, tribeDes means using
                     3DES encryption."
        ::= { sshConnInfoEntry 4 }
--sshv1 only end

--both sshv1 & sshv2 start


sshConnUserName OBJECT-TYPE
        SYNTAX      DisplayString(SIZE(1..8))
        MAX-ACCESS  read-only
        STATUS      current
        DESCRIPTION "The user name of the connection."
        ::= { sshConnInfoEntry 6 }

sshDisconnect OBJECT-TYPE
        SYNTAX      INTEGER
                    {
                      noDisconnect(1),
                      disconnect(2)
                    }
        MAX-ACCESS  read-write
        STATUS      current
        DESCRIPTION "Set the variable to disconnect the connection,
                     noDisconnect(1) will always be obtained when reading this variable."
        ::= { sshConnInfoEntry 7 }

--both sshv1 & sshv2 end

--sshv2 only start
sshConnEncryptionTypeStr  OBJECT-TYPE
SYNTAX      DisplayString(SIZE(0..64))
        MAX-ACCESS  read-only
        STATUS      current
        DESCRIPTION "The encryption type of the SSH."
        ::= { sshConnInfoEntry 8 }


sshKeySize OBJECT-TYPE
        SYNTAX      INTEGER(512..896)
        MAX-ACCESS  read-write
        STATUS      current
        DESCRIPTION "The SSH server key size."
        ::= { sshMgt 7 }


sshRsaHostKey1 OBJECT-TYPE
        SYNTAX      KeySegment
        MAX-ACCESS  read-only
        STATUS      current
        DESCRIPTION "The RSA host key segment 1."
        ::= { sshMgt 8 }

sshRsaHostKey2 OBJECT-TYPE
        SYNTAX      KeySegment
        MAX-ACCESS  read-only
        STATUS      current
        DESCRIPTION "The RSA host key segment 2."
        ::= { sshMgt 9 }

sshRsaHostKey3 OBJECT-TYPE
        SYNTAX      KeySegment
        MAX-ACCESS  read-only
        STATUS      current
        DESCRIPTION "The RSA host key segment 3."
        ::= { sshMgt 10 }

sshRsaHostKey4 OBJECT-TYPE
        SYNTAX      KeySegment
        MAX-ACCESS  read-only
        STATUS      current
        DESCRIPTION "The RSA host key segment 4."
        ::= { sshMgt 11 }

sshRsaHostKey5 OBJECT-TYPE
        SYNTAX      KeySegment
        MAX-ACCESS  read-only
        STATUS      current
        DESCRIPTION "The RSA host key segment 5."
        ::= { sshMgt 12 }

sshRsaHostKey6 OBJECT-TYPE
        SYNTAX      KeySegment
        MAX-ACCESS  read-only
        STATUS      current
        DESCRIPTION "The RSA host key segment 6."
        ::= { sshMgt 13 }

sshRsaHostKey7 OBJECT-TYPE
        SYNTAX      KeySegment
        MAX-ACCESS  read-only
        STATUS      current
        DESCRIPTION "The RSA host key segment 7."
        ::= { sshMgt 14 }

sshRsaHostKey8 OBJECT-TYPE
        SYNTAX      KeySegment
        MAX-ACCESS  read-only
        STATUS      current
        DESCRIPTION "The RSA host key segment 8."
        ::= { sshMgt 15 }

sshDsaHostKey1 OBJECT-TYPE
        SYNTAX      KeySegment
        MAX-ACCESS  read-only
        STATUS      current
        DESCRIPTION "The DSA host key segment 1."
        ::= { sshMgt 16 }

sshDsaHostKey2 OBJECT-TYPE
        SYNTAX      KeySegment
        MAX-ACCESS  read-only
        STATUS      current
        DESCRIPTION "The DSA host key segment 2."
        ::= { sshMgt 17 }

sshDsaHostKey3 OBJECT-TYPE
        SYNTAX      KeySegment
        MAX-ACCESS  read-only
        STATUS      current
        DESCRIPTION "The DSA host key segment 3."
        ::= { sshMgt 18 }

sshDsaHostKey4 OBJECT-TYPE
        SYNTAX      KeySegment
        MAX-ACCESS  read-only
        STATUS      current
        DESCRIPTION "The DSA host key segment 4."
        ::= { sshMgt 19 }

sshDsaHostKey5 OBJECT-TYPE
        SYNTAX      KeySegment
        MAX-ACCESS  read-only
        STATUS      current
        DESCRIPTION "The DSA host key segment 5."
        ::= { sshMgt 20 }

sshDsaHostKey6 OBJECT-TYPE
        SYNTAX      KeySegment
        MAX-ACCESS  read-only
        STATUS      current
        DESCRIPTION "The DSA host key segment 6."
        ::= { sshMgt 21 }

sshDsaHostKey7 OBJECT-TYPE
        SYNTAX      KeySegment
        MAX-ACCESS  read-only
        STATUS      current
        DESCRIPTION "The DSA host key segment 7."
        ::= { sshMgt 22 }

sshDsaHostKey8 OBJECT-TYPE
        SYNTAX      KeySegment
        MAX-ACCESS  read-only
        STATUS      current
        DESCRIPTION "The DSA host key segment 8."
        ::= { sshMgt 23 }

sshHostKeyGenAction OBJECT-TYPE
        SYNTAX      INTEGER
                    {
                        noGen(1),
                        genRsaKey(2),
                        genDsaKey(3),
                        genBothKeys(4)
                    }
        MAX-ACCESS  read-write
        STATUS      current
        DESCRIPTION "This variable is for host key generating.

                    For the set behavior:
                    Set it to genRsaKey(2) to generate the RSA host key,
                    and to genDsaKey(3) to generate the DSA host key,
                    if genBothKeys(4) is set, both RSA and DSA host key are
                    generated.

                    For the get behavior:
                    You will get genRsaKey(2), genDsaKey(3) or
                    genBothKeys(4) when the key gen action is in progress.
                    otherwise, you will get noGen(1)."
        ::= { sshMgt 24 }

sshHostKeyGenStatus OBJECT-TYPE
        SYNTAX      INTEGER
                    {
                        unknown(1),
                        success(2),
                        failure(3)
                    }
        MAX-ACCESS  read-only
        STATUS      current
        DESCRIPTION "The result of the last KeyGen status.
                     if no key gen action has been performed.
                     you will get unknown(1) status."
        ::= { sshMgt 25 }

sshHostKeySaveAction OBJECT-TYPE
        SYNTAX      INTEGER
                    {
                        noSave(1),
                        save(2)
                    }
        MAX-ACCESS  read-write
        STATUS      current
        DESCRIPTION "To save host key from memory to flash.

                     For the set behavior:
                     Set it to save(2) to perform the save operation.

                     For the get behavior:
                     You will get save(1) when the save action is in progress.
                     Otherwise, you will get noSave(1)."
        ::= { sshMgt 26 }

sshHostKeySaveStatus OBJECT-TYPE
        SYNTAX      INTEGER
                    {
                        unknown(1),
                        success(2),
                        failure(3)
                    }
        MAX-ACCESS  read-only
        STATUS      current
        DESCRIPTION "The result of the last savekey status.
                     If no save action has been performed,
                     you will get unknown(1) status."
        ::= { sshMgt 27 }

sshHostKeyDelAction  OBJECT-TYPE
        SYNTAX      INTEGER
                    {
                        noDel(1),
                        delRsaKey(2),
                        delDsaKey(3),
                        delBothKeys(4)
                    }
        MAX-ACCESS  read-write
        STATUS      current
        DESCRIPTION "To delete the host key.

                     For the set behavior:
                     Set it to delRsaKey(2) to delete the RSA host key,
                     to delDsaKey(3) to delete the DSA host key,
                     or to delBothKeys(4) to delete both RSA and DSA host key.

                     For the get behavior:
                     You will get delRsaKey(2), delDsaKey(3) or  delBothKeys(4)
                     when the delete operation is in progress.
                     Otherwise, you will get noDel(1)."
        ::= { sshMgt 28 }

sshUserTable OBJECT-TYPE
        SYNTAX      SEQUENCE OF SshUserEntry
        MAX-ACCESS  not-accessible
        STATUS      current
        DESCRIPTION "The conceptual table of all of sshUserEntry."
        ::= { sshMgt 29 }

sshUserEntry OBJECT-TYPE
        SYNTAX      SshUserEntry
        MAX-ACCESS  not-accessible
        STATUS      current
        DESCRIPTION "The conceptual row for sshUserTable."
        INDEX       { IMPLIED sshUserName}
        ::= { sshUserTable 1 }

SshUserEntry ::= SEQUENCE
{
    sshUserName             DisplayString,
    sshUserRsaKey1          KeySegment,
    sshUserRsaKey2          KeySegment,
    sshUserRsaKey3          KeySegment,
    sshUserRsaKey4          KeySegment,
    sshUserRsaKey5          KeySegment,
    sshUserRsaKey6          KeySegment,
    sshUserRsaKey7          KeySegment,
    sshUserRsaKey8          KeySegment,
    sshUserDsaKey1          KeySegment,
    sshUserDsaKey2          KeySegment,
    sshUserDsaKey3          KeySegment,
    sshUserDsaKey4          KeySegment,
    sshUserDsaKey5          KeySegment,
    sshUserDsaKey6          KeySegment,
    sshUserDsaKey7          KeySegment,
    sshUserDsaKey8          KeySegment,
    sshUserKeyDelAction     INTEGER
}

sshUserName OBJECT-TYPE
        SYNTAX      DisplayString(SIZE(1..8))
        MAX-ACCESS  not-accessible
        STATUS      current
        DESCRIPTION "User Name."
        ::= { sshUserEntry 1 }

sshUserRsaKey1 OBJECT-TYPE
        SYNTAX      KeySegment
        MAX-ACCESS  read-only
        STATUS      current
        DESCRIPTION "The RSA user key segment 1."
        ::= { sshUserEntry 2 }

sshUserRsaKey2 OBJECT-TYPE
        SYNTAX      KeySegment
        MAX-ACCESS  read-only
        STATUS      current
        DESCRIPTION "The RSA user key segment 2."
        ::= { sshUserEntry 3 }

sshUserRsaKey3 OBJECT-TYPE
        SYNTAX      KeySegment
        MAX-ACCESS  read-only
        STATUS      current
        DESCRIPTION "The RSA user key segment 3."
        ::= { sshUserEntry 4 }

sshUserRsaKey4 OBJECT-TYPE
        SYNTAX      KeySegment
        MAX-ACCESS  read-only
        STATUS      current
        DESCRIPTION "The RSA user key segment 4."
        ::= { sshUserEntry 5 }

sshUserRsaKey5 OBJECT-TYPE
        SYNTAX      KeySegment
        MAX-ACCESS  read-only
        STATUS      current
        DESCRIPTION "The RSA user key segment 5."
        ::= { sshUserEntry 6 }

sshUserRsaKey6 OBJECT-TYPE
        SYNTAX      KeySegment
        MAX-ACCESS  read-only
        STATUS      current
        DESCRIPTION "The RSA user key segment 6."
        ::= { sshUserEntry 7 }

sshUserRsaKey7 OBJECT-TYPE
        SYNTAX      KeySegment
        MAX-ACCESS  read-only
        STATUS      current
        DESCRIPTION "The RSA user key segment 7."
        ::= { sshUserEntry 8 }

sshUserRsaKey8 OBJECT-TYPE
        SYNTAX      KeySegment
        MAX-ACCESS  read-only
        STATUS      current
        DESCRIPTION "The RSA user key segment 8."
        ::= { sshUserEntry 9 }

sshUserDsaKey1 OBJECT-TYPE
        SYNTAX      KeySegment
        MAX-ACCESS  read-only
        STATUS      current
        DESCRIPTION "The DSA user key segment 1."
        ::= { sshUserEntry 10 }

sshUserDsaKey2 OBJECT-TYPE
        SYNTAX      KeySegment
        MAX-ACCESS  read-only
        STATUS      current
        DESCRIPTION "The DSA user key segment 2."
        ::= { sshUserEntry 11 }

sshUserDsaKey3 OBJECT-TYPE
        SYNTAX      KeySegment
        MAX-ACCESS  read-only
        STATUS      current
        DESCRIPTION "The DSA user key segment 3."
        ::= { sshUserEntry 12 }

sshUserDsaKey4 OBJECT-TYPE
        SYNTAX      KeySegment
        MAX-ACCESS  read-only
        STATUS      current
        DESCRIPTION "The DSA user key segment 4."
        ::= { sshUserEntry 13 }

sshUserDsaKey5 OBJECT-TYPE
        SYNTAX      KeySegment
        MAX-ACCESS  read-only
        STATUS      current
        DESCRIPTION "The DSA user key segment 5."
        ::= { sshUserEntry 14 }

sshUserDsaKey6 OBJECT-TYPE
        SYNTAX      KeySegment
        MAX-ACCESS  read-only
        STATUS      current
        DESCRIPTION "The DSA user key segment 6."
        ::= { sshUserEntry 15 }

sshUserDsaKey7 OBJECT-TYPE
        SYNTAX      KeySegment
        MAX-ACCESS  read-only
        STATUS      current
        DESCRIPTION "The DSA user key segment 7."
        ::= { sshUserEntry 16 }

sshUserDsaKey8 OBJECT-TYPE
        SYNTAX      KeySegment
        MAX-ACCESS  read-only
        STATUS      current
        DESCRIPTION "The DSA user key segment 8."
        ::= { sshUserEntry 17 }

sshUserKeyDelAction  OBJECT-TYPE
        SYNTAX      INTEGER
                    {
                        noDel(1),
                        delRsaKey(2),
                        delDsaKey(3),
                        delBothKeys(4)
                    }
        MAX-ACCESS  read-write
        STATUS      current
        DESCRIPTION "To delete the user key.

                     For the set behavior:
                     Set it to delRsaKey(2) to delete the RSA user key,
                     to delDsaKey(3) to delete the DSA user key,
                     or to delBothKeys(4) to delete both RSA and DSA user key.

                     For the get behavior:
                     You will get delRsaKey(2), delDsaKey(3) or  delBothKeys(4)
                     when the delete operation is in progress.
                     Otherwise, you will get noDel(1)."
        ::= { sshUserEntry 18 }

sshRsaHostKeySHA1FingerPrint OBJECT-TYPE
       SYNTAX     DisplayString(SIZE(65))
       MAX-ACCESS read-only
       STATUS     current
       DESCRIPTION "The SHA1 finger print of the RSA host key."
       ::= { sshMgt 30 }

sshRsaHostKeyMD5FingerPrint OBJECT-TYPE
       SYNTAX     DisplayString(SIZE(47))
       MAX-ACCESS read-only
       STATUS     current
       DESCRIPTION "The MD5 finger print of RSA host key."
       ::= { sshMgt 31 }

sshDsaHostKeySHA1FingerPrint OBJECT-TYPE
       SYNTAX     DisplayString(SIZE(65))
       MAX-ACCESS read-only
       STATUS     current
       DESCRIPTION "The SHA1 finger print of the DSA host key."
       ::= { sshMgt 32 }

sshDsaHostKeyMD5FingerPrint OBJECT-TYPE
       SYNTAX     DisplayString(SIZE(47))
       MAX-ACCESS read-only
       STATUS     current
       DESCRIPTION "The MD5 finger print of the DSA host key."
       ::= { sshMgt 33 }
--sshv2 only end

--
-- aclMgt
--

--aclIpAceTable
aclIpAceTable       OBJECT-TYPE
        SYNTAX      SEQUENCE OF AclIpAceEntry
        MAX-ACCESS  not-accessible
        STATUS      current
        DESCRIPTION "The conceptual table of all of aclIpAceEntry."
        ::= { aclMgt 1 }

aclIpAceEntry OBJECT-TYPE
        SYNTAX      AclIpAceEntry
        MAX-ACCESS  not-accessible
        STATUS      current
        DESCRIPTION "The conceptual row for aclIpAceTable."
        INDEX       { aclIpAceName, aclIpAceIndex }
        ::= { aclIpAceTable 1 }

AclIpAceEntry ::= SEQUENCE
{
    aclIpAceName                    DisplayString,
    aclIpAceIndex                   Integer32,
    aclIpAcePrecedence              Integer32,
    aclIpAceAction                  INTEGER,
    aclIpAceSourceIpAddr            IpAddress,
    aclIpAceSourceIpAddrBitmask     IpAddress,
    aclIpAceDestIpAddr              IpAddress,
    aclIpAceDestIpAddrBitmask       IpAddress,
    aclIpAceProtocol                Integer32,
    aclIpAcePrec                    Integer32,
    aclIpAceTos                     Integer32,
    aclIpAceDscp                    Integer32,
    aclIpAceSourcePortOp            INTEGER,
    aclIpAceMinSourcePort           Integer32,
    aclIpAceMaxSourcePort           Integer32,
    aclIpAceSourcePortBitmask       Integer32,
    aclIpAceDestPortOp              INTEGER,
    aclIpAceMinDestPort             Integer32,
    aclIpAceMaxDestPort             Integer32,
    aclIpAceDestPortBitmask         Integer32,
    aclIpAceControlCode             Integer32,
    aclIpAceControlCodeBitmask      Integer32,
    aclIpAceStatus                  RowStatus
}

aclIpAceName OBJECT-TYPE
        SYNTAX      DisplayString (SIZE(1..16))
        MAX-ACCESS  not-accessible
        STATUS      current
        DESCRIPTION "The name of an ACL. Within a feature a unique
                     name is used to identify
                     the list to which the entry belongs in the device."
        ::= { aclIpAceEntry 1 }

aclIpAceIndex OBJECT-TYPE
        SYNTAX      Integer32 (1..32)
        MAX-ACCESS  not-accessible
        STATUS      current
        DESCRIPTION "The unique index of an ACE within an ACL."
        ::= { aclIpAceEntry 2 }

aclIpAcePrecedence OBJECT-TYPE
        SYNTAX      Integer32 (0..32)
        MAX-ACCESS  read-only
        STATUS      current
        DESCRIPTION "Specifies the precedence in which to check for matching IP ACE."
        ::= { aclIpAceEntry 3 }

aclIpAceAction OBJECT-TYPE
        SYNTAX      INTEGER
                    {
                        permit(1),
                        deny(2)
                    }
        MAX-ACCESS  read-create
        STATUS      current
        DESCRIPTION "Indicates the action to be taken if a packet matches this ACE.
                     This object cannot not be configured when the status of the
                     entry, aclIpAceStatus, is active(1)."
        ::= { aclIpAceEntry 4 }

aclIpAceSourceIpAddr OBJECT-TYPE
        SYNTAX      IpAddress
        MAX-ACCESS  read-create
        STATUS      current
        DESCRIPTION "The specified source IP address. The packet's source address is
                    AND-ed with the value of aclIpAceSourceIpAddrBitmask and then compared
                    against the value of this object.
                    This object cannot be configured when the status of the
                    entry, aclIpAceStatus, is active(1)."
        ::= { aclIpAceEntry 5 }

aclIpAceSourceIpAddrBitmask OBJECT-TYPE
        SYNTAX      IpAddress
        MAX-ACCESS  read-create
        STATUS      current
        DESCRIPTION "The specified source IP address mask. The packet's destination
                     address is AND-ed with the value of aclIpAceSourceIpAddr and then
                     compared against the value of this object."
        ::= { aclIpAceEntry 6 }

aclIpAceDestIpAddr OBJECT-TYPE
        SYNTAX      IpAddress
        MAX-ACCESS  read-create
        STATUS      current
        DESCRIPTION "The specified destination IP address.
                     The packet's destination address is
                     AND-ed with the value of aclIpAceDestIpAddrBitmask and then compared
                     against the value of this object."
        ::= { aclIpAceEntry 7 }

aclIpAceDestIpAddrBitmask OBJECT-TYPE
        SYNTAX      IpAddress
        MAX-ACCESS  read-create
        STATUS      current
        DESCRIPTION "The specified destination IP address mask."
        ::= { aclIpAceEntry 8 }

aclIpAceProtocol OBJECT-TYPE
        SYNTAX      Integer32 (0..256)
        MAX-ACCESS  read-create
        STATUS      current
        DESCRIPTION "The protocol number field in the IP header used to indicate
                    the higher layer protocol as specified in RFC 1700. A value
                    value of 0 matches every IP packet. The object=256, means 'any'

                    For example :
                    0 is IP, 1 is ICMP, 2 is IGMP, 4 is IP in IP encapsulation,
                    6 is TCP, 9 is IGRP, 17 is UDP, 47 is GRE, 50 is ESP, 51 is AH,
                    88 is IGRP, 89 is OSPF, 94 is KA9Q/NOS compatible IP over IP,
                    103 is PIMv2, 108 is PCP."
        ::= { aclIpAceEntry 9 }

aclIpAcePrec OBJECT-TYPE
        SYNTAX      Integer32 (0..8)
        MAX-ACCESS  read-create
        STATUS      current
        DESCRIPTION "Specifies the IP precedence value to be matched against.
                     This object cannot be configured when the status of the
                     entry, aclIpAceStatus, is active(1).
                     The value of this object is ignored whenever the value of
                     aclIpAcePrec object is 8."
        ::= { aclIpAceEntry 10 }

aclIpAceTos OBJECT-TYPE
        SYNTAX      Integer32 (0..16)
        MAX-ACCESS  read-create
        STATUS      current
        DESCRIPTION "Specifies the IP ToS facility value to be matched against.
                     This object cannot be configured when the status of the
                     entry, aclIpAceStatus, is active(1).
                     The value of this object is ignored whenever the value of
                     aclIpAcePrec object is 9."
        ::= { aclIpAceEntry 11 }

aclIpAceDscp OBJECT-TYPE
        SYNTAX      Integer32 (0..64)
        MAX-ACCESS  read-create
        STATUS      current
        DESCRIPTION "Specifies the DSCP value to be matched against.
                     This object cannot be configured when the status of the
                     entry, aclIpAceStatus, is active(1).
                     The value of this object is ignored whenever the value of
                     aclIpAcePrec object is 64."
        ::= { aclIpAceEntry 12 }

aclIpAceSourcePortOp OBJECT-TYPE
        SYNTAX      INTEGER
                    {
                        noOperator(1),
                        equal(2),
                        range(3)
                    }
        MAX-ACCESS  read-create
        STATUS      current
        DESCRIPTION "Indicates how a packet's source TCP/UDP port number is
                     to be compared. noOperator(1), which is the default value, means no
                     comparison is to be made with the source TCP/UDP port
                     number."
        ::= { aclIpAceEntry 13 }

aclIpAceMinSourcePort OBJECT-TYPE
        SYNTAX      Integer32 (0..'FFFF'h)
        MAX-ACCESS  read-create
        STATUS      current
        DESCRIPTION "If the aclIpAceSourcePortOp is range(3),
                     this indicates the lower bound of the TCP/UDP port number value range."
        ::= { aclIpAceEntry 14 }

aclIpAceMaxSourcePort OBJECT-TYPE
        SYNTAX      Integer32 (0..'FFFF'h)
        MAX-ACCESS  read-create
        STATUS      current
        DESCRIPTION "If the aclIpAceSourcePortOp is range(3),
                     this indicates the upper bound of the TCP/UDP port number value range."
        ::= { aclIpAceEntry 15 }

aclIpAceSourcePortBitmask OBJECT-TYPE
        SYNTAX      Integer32 (0..'FFFF'h)
        MAX-ACCESS  read-create
        STATUS      current
        DESCRIPTION "If the aclIpAceSourcePortOp is equal(2),
                    this indicates the bitmask of the aclIpAceMinSourcePort."
        ::= { aclIpAceEntry 16 }

aclIpAceDestPortOp OBJECT-TYPE
        SYNTAX      INTEGER
                    {
                        noOperator(1),
                        equal(2),
                        range(3)
                    }
        MAX-ACCESS  read-create
        STATUS      current
        DESCRIPTION "Indicates how a packet's destination TCP/UDP port number is
                     to be compared. noOperator(1), which is the default value, means that no
                     comparison is to be made with the destination TCP/UDP port
                     number."
        ::= { aclIpAceEntry 17 }

aclIpAceMinDestPort OBJECT-TYPE
        SYNTAX      Integer32 (0..'FFFF'h)
        MAX-ACCESS  read-create
        STATUS      current
        DESCRIPTION "If the aclIpAceDestPortOp is range(3),
                     this indicates the lower bound of the TCP/UDP port number value range."
        ::= { aclIpAceEntry 18 }

aclIpAceMaxDestPort OBJECT-TYPE
        SYNTAX      Integer32 (0..'FFFF'h)
        MAX-ACCESS  read-create
        STATUS      current
        DESCRIPTION "If the aclIpAceDestPortOp is range(3),
                     this indicates the upper bound of the TCP/UDP port number value range."
        ::= { aclIpAceEntry 19 }

aclIpAceDestPortBitmask OBJECT-TYPE
        SYNTAX      Integer32 (0..'FFFF'h)
        MAX-ACCESS  read-create
        STATUS      current
        DESCRIPTION "If the aclIpAceDestPortOp is equal(2),
                     this indicates the bitmask of the aclIpAceMinDestPort."
        ::= { aclIpAceEntry 20 }

aclIpAceControlCode OBJECT-TYPE
        SYNTAX      Integer32 (0..63)
        MAX-ACCESS  read-create
        STATUS      current
        DESCRIPTION "Indicates how the control flags of TCP packets are to be compared.
                     aceIpControlCode is AND-ed with aceIpControlCodeBitmask."
        ::= { aclIpAceEntry 21 }

aclIpAceControlCodeBitmask OBJECT-TYPE
        SYNTAX      Integer32 (0..63)
        MAX-ACCESS  read-create
        STATUS      current
        DESCRIPTION "Indicates how the control flags of TCP packets are to be compared.
                     It can be used to check multiple flags of the
                     FIN, SYN, RST, PSH, ACK, URG by the sum of
                     FIN=1, SYN=2, RST=4, PSH=8, ACK=16, URG=32."
        ::= { aclIpAceEntry 22 }

aclIpAceStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { aclIpAceEntry 23 }

-- aclMacAceTable
aclMacAceTable OBJECT-TYPE
        SYNTAX      SEQUENCE OF AclMacAceEntry
        MAX-ACCESS  not-accessible
        STATUS      current
        DESCRIPTION "The conceptual table of all of aclMacAceEntry."
        ::= { aclMgt 2 }

aclMacAceEntry OBJECT-TYPE
        SYNTAX      AclMacAceEntry
        MAX-ACCESS  not-accessible
        STATUS      current
        DESCRIPTION "The conceptual row for aclMacAceTable."
        INDEX       { aclMacAceName, aclMacAceIndex }
        ::= { aclMacAceTable 1 }

AclMacAceEntry ::= SEQUENCE
{
    aclMacAceName                   DisplayString,
    aclMacAceIndex                  Integer32,
    aclMacAcePrecedence             Integer32,
    aclMacAceAction                 INTEGER,
    aclMacAcePktformat              INTEGER,
    aclMacAceSourceMacAddr          OCTET STRING,
    aclMacAceSourceMacAddrBitmask   OCTET STRING,
    aclMacAceDestMacAddr            OCTET STRING,
    aclMacAceDestMacAddrBitmask     OCTET STRING,
    aclMacAceVidOp                  INTEGER,
    aclMacAceMinVid                 Integer32,
    aclMacAceVidBitmask             Integer32,
    aclMacAceMaxVid                 Integer32,
    aclMacAceEtherTypeOp            INTEGER,
    aclMacAceEtherTypeBitmask       Integer32,
    aclMacAceMinEtherType           Integer32,
    aclMacAceMaxEtherType           Integer32,
    aclMacAceStatus                 RowStatus
}

aclMacAceName OBJECT-TYPE
        SYNTAX      DisplayString (SIZE(1..16))
        MAX-ACCESS  not-accessible
        STATUS      current
        DESCRIPTION "The name of an ACL. Within a feature, a unique
                    name is used to identify
                    the list to which the entry belongs in the device."
        ::= { aclMacAceEntry 1 }

aclMacAceIndex OBJECT-TYPE
        SYNTAX      Integer32 (1..32)
        MAX-ACCESS  not-accessible
        STATUS      current
        DESCRIPTION "The unique index of an ACE within an ACL."
        ::= { aclMacAceEntry 2 }

aclMacAcePrecedence OBJECT-TYPE
        SYNTAX      Integer32 (0..32)
        MAX-ACCESS  read-only
        STATUS      current
        DESCRIPTION "Specifies the entry's precedence."
        ::= { aclMacAceEntry 3 }

aclMacAceAction OBJECT-TYPE
        SYNTAX      INTEGER
                    {
                        permit(1),
                        deny(2)
                    }
        MAX-ACCESS  read-create
        STATUS      current
        DESCRIPTION "Indicates the action to be taken if a packet matches this ACE.
                     This object cannot be configured when the status of the
                     entry, aclMacAceStatus, is active(1)."
        ::= { aclMacAceEntry 4 }

aclMacAcePktformat OBJECT-TYPE
        SYNTAX      INTEGER
                    {
                        any(1),
                        untagged-Eth2(2),
                        untagged802Dot3(3),
                        tagggedEth2(4),
                        tagged802Dot3(5)
                    }
        MAX-ACCESS  read-create
        STATUS      current
        DESCRIPTION "Used to check the packet format of the packets.
                     This object cannot be configured when the status of the
                     entry, aclMacAceStatus, is active(1)."
        ::= { aclMacAceEntry 5 }

aclMacAceSourceMacAddr OBJECT-TYPE
        SYNTAX      OCTET STRING (SIZE (6))
        MAX-ACCESS  read-create
        STATUS      current
        DESCRIPTION "Indicates the 48-bit destination MAC address.
                    The specified source MAC of the packet The packet's source MAC
                    address is AND-ed with the value of aceMacSourceMacAddrBitmask
                    and then compared against the value of this object. This object
                    cannot be configured when the status of the entry,
                    aclMacAceStatus, is active(1)."
        ::= { aclMacAceEntry 6 }

aclMacAceSourceMacAddrBitmask OBJECT-TYPE
        SYNTAX      OCTET STRING (SIZE (6))
        MAX-ACCESS  read-create
        STATUS      current
        DESCRIPTION "The specified source MAC address mask.
                    This object cannot be configured when the status of the
                    entry, aclMacAceStatus, is active(1)."
        ::= { aclMacAceEntry 7 }

aclMacAceDestMacAddr OBJECT-TYPE
        SYNTAX      OCTET STRING (SIZE (6))
        MAX-ACCESS  read-create
        STATUS      current
        DESCRIPTION "Indicates the 48-bit destination MAC address.
                     The specified destination MAC of the packet.
                     The packet's destination MAC address is
                     AND-ed with the value of aceMacDestMacAddrBitmask and then compared
                     against the value of this object.
                     This object cannot be configured when the status of the
                     entry, aclMacAceStatus, is active(1)."
        ::= { aclMacAceEntry 8 }

aclMacAceDestMacAddrBitmask OBJECT-TYPE
        SYNTAX      OCTET STRING (SIZE (6))
        MAX-ACCESS  read-create
        STATUS      current
        DESCRIPTION "The specified destination MAC address mask.
                     This object cannot be configured when the status of the
                     entry, aclMacAceStatus, is active(1)."
        ::= { aclMacAceEntry 9 }

aclMacAceVidOp OBJECT-TYPE
        SYNTAX      INTEGER
                    {
                        noOperator(1),
                        equal(2),
                        range(3)
                    }
        MAX-ACCESS  read-create
        STATUS      current
        DESCRIPTION "Indicates how a packet's vid is
                     to be compared.
                     This object cannot be configured when the status of the
                     entry, aclMacAceStatus, is active(1)."
        ::= { aclMacAceEntry 10 }

aclMacAceMinVid OBJECT-TYPE
        SYNTAX      Integer32 (1..'0FFF'h)
        MAX-ACCESS  read-create
        STATUS      current
        DESCRIPTION "Indicates the lower bound of the vid value range if the aclMacAceVidOp is range(3).
                     This object cannot be configured when the status of the
                     entry, aclMacAceStatus, is active(1)."
        ::= { aclMacAceEntry 11 }

aclMacAceVidBitmask OBJECT-TYPE
        SYNTAX      Integer32 (0..'0FFF'h)
        MAX-ACCESS  read-create
        STATUS      current
        DESCRIPTION "The bitmask of vid if the aclMacAceVidOp is equal, default value is 0xfff."
        ::= { aclMacAceEntry 12 }

aclMacAceMaxVid OBJECT-TYPE
        SYNTAX      Integer32 (1..'0FFF'h)
        MAX-ACCESS  read-create
        STATUS      current
        DESCRIPTION "Indicates the upper bound of the vid value range if the aclMacAceVidOp is range(3).
                     This object cannot be configured when the status of the
                     entry, aclMacAceStatus, is active(1)."
        ::= { aclMacAceEntry 13 }

aclMacAceEtherTypeOp OBJECT-TYPE
        SYNTAX      INTEGER
                    {
                        noOperator(1),
                        equal(2),
                        range(3)
                    }
        MAX-ACCESS  read-create
        STATUS      current
        DESCRIPTION "Indicates how a packet's ethertype is
                     to be compared.
                     This object cannot be configured when the status of the
                     entry, aclMacAceStatus, is active(1)."
        ::= { aclMacAceEntry 14 }

aclMacAceEtherTypeBitmask OBJECT-TYPE
        SYNTAX      Integer32 (0..'FFFF'h)
        MAX-ACCESS  read-create
        STATUS      current
        DESCRIPTION "The bitmask of ether type if the aclMacAceVidOp is equal(2) , default value is 0xFFFF."
        ::= { aclMacAceEntry 15 }

aclMacAceMinEtherType OBJECT-TYPE
        SYNTAX      Integer32 ('0600'h..'FFFF'h)
        MAX-ACCESS  read-create
        STATUS      current
        DESCRIPTION "Indicates the lower bound of the ether type value range if the aclMacAceEtherTypeOp is range(3).
                     This object cannot be configured when the status of the
                     entry, aclMacAceStatus, is active(1)."
        ::= { aclMacAceEntry 16 }

aclMacAceMaxEtherType OBJECT-TYPE
        SYNTAX      Integer32 ('0600'h..'FFFF'h)
        MAX-ACCESS  read-create
        STATUS      current
        DESCRIPTION "Indicates the upper bound of the ether type value range if the aclMacAceEtherTypeOp is range(3).
                     This object cannot be configured when the status of the
                     entry, aclMacAceStatus, is active(1)."
        ::= { aclMacAceEntry 17 }

aclMacAceStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { aclMacAceEntry 18 }

--aclAclGroupTable
aclAclGroupTable OBJECT-TYPE
        SYNTAX      SEQUENCE OF AclAclGroupEntry
        MAX-ACCESS  not-accessible
        STATUS      current
        DESCRIPTION "The conceptual table of aclAclGroupEntry."
        ::= { aclMgt 3 }

aclAclGroupEntry OBJECT-TYPE
        SYNTAX      AclAclGroupEntry
        MAX-ACCESS  not-accessible
        STATUS      current
        DESCRIPTION "The conceptual row for aclAclGroupTable."
        INDEX       { aclAclGroupIfIndex }
        ::= { aclAclGroupTable 1 }

AclAclGroupEntry ::= SEQUENCE
{
    aclAclGroupIfIndex Integer32,
    aclAclGroupIngressIpAcl DisplayString,
    aclAclGroupEgressIpAcl DisplayString,
    aclAclGroupIngressMacAcl DisplayString,
    aclAclGroupEgressMacAcl DisplayString
}

aclAclGroupIfIndex OBJECT-TYPE
        SYNTAX      Integer32
        MAX-ACCESS  not-accessible
        STATUS      current
        DESCRIPTION "The interface number specifying the ACL binding to."
        ::= { aclAclGroupEntry 1 }

aclAclGroupIngressIpAcl OBJECT-TYPE
        SYNTAX      DisplayString (SIZE(0..15))
        MAX-ACCESS  read-write
        STATUS      current
        DESCRIPTION "Specifies the ingress IP ACL(standard or extended) binding to the interface."
        ::= { aclAclGroupEntry 2 }

aclAclGroupEgressIpAcl OBJECT-TYPE
        SYNTAX      DisplayString (SIZE(0..15))
        MAX-ACCESS  read-write
        STATUS      current
        DESCRIPTION "Specifies the egress IP ACL(standard or extended) binding to the interface."
        ::= { aclAclGroupEntry 3 }

aclAclGroupIngressMacAcl OBJECT-TYPE
        SYNTAX      DisplayString (SIZE(0..15))
        MAX-ACCESS  read-write
        STATUS      current
        DESCRIPTION "Specifies the ingress MAC ACL binding to the interface."
        ::= { aclAclGroupEntry 4 }

aclAclGroupEgressMacAcl OBJECT-TYPE
        SYNTAX      DisplayString (SIZE(0..15))
        MAX-ACCESS  read-write
        STATUS      current
        DESCRIPTION "Specifies the egress MAC ACL binding to the interface."
        ::= { aclAclGroupEntry 5 }

--aclIngressIpMaskTable
aclIngressIpMaskTable OBJECT-TYPE
        SYNTAX      SEQUENCE OF AclIngressIpMaskEntry
        MAX-ACCESS  not-accessible
        STATUS      current
        DESCRIPTION "The conceptual table of aclIngressIpMaskEntry."
        ::= { aclMgt 4 }

aclIngressIpMaskEntry OBJECT-TYPE
        SYNTAX      AclIngressIpMaskEntry
        MAX-ACCESS  not-accessible
        STATUS      current
        DESCRIPTION "The conceptual row for aclIngressIpMaskTable."
        INDEX       { aclIngressIpMaskIndex }
        ::= { aclIngressIpMaskTable 1 }

AclIngressIpMaskEntry ::= SEQUENCE
{
    aclIngressIpMaskIndex               Integer32,
    aclIngressIpMaskPrecedence          Integer32,
    aclIngressIpMaskIsEnableTos         EnabledStatus,
    aclIngressIpMaskIsEnableDscp        EnabledStatus,
    aclIngressIpMaskIsEnablePrecedence  EnabledStatus,
    aclIngressIpMaskIsEnableProtocol    EnabledStatus,
    aclIngressIpMaskSourceIpAddrBitmask IpAddress,
    aclIngressIpMaskDestIpAddrBitmask   IpAddress,
    aclIngressIpMaskSourcePortBitmask   Integer32,
    aclIngressIpMaskDestPortBitmask     Integer32,
    aclIngressIpMaskControlCodeBitmask  Integer32,
    aclIngressIpMaskStatus              RowStatus
}

aclIngressIpMaskIndex OBJECT-TYPE
        SYNTAX      Integer32 (1..16)
        MAX-ACCESS  not-accessible
        STATUS      current
        DESCRIPTION "The index of a mask entry within an ingress IP mask table."
        ::= { aclIngressIpMaskEntry 1 }

aclIngressIpMaskPrecedence OBJECT-TYPE
        SYNTAX      Integer32 (0..16)
        MAX-ACCESS  read-only
        STATUS      current
        DESCRIPTION "Indicates whether to check the IP precedence against the packets,
                     The relative bitmask must be created before the
                     ACE binds to the interface in ingress direction.
                     This object cannot be configured
                     when the status of the entry, aclIngressIpMaskStatus, is active(1)."
        ::= { aclIngressIpMaskEntry 2 }

aclIngressIpMaskIsEnableTos OBJECT-TYPE
        SYNTAX      EnabledStatus
        MAX-ACCESS  read-create
        STATUS      current
        DESCRIPTION "Indicates whether to check the IP ToS facility against the packets,
                     The relative bitmask must be created before the
                    ACE binds to the interface in ingress direction.
                     This object cannot be configured when the status of the
                     entry, aclIngressIpMaskStatus, is active(1)."
        ::= { aclIngressIpMaskEntry 3 }

aclIngressIpMaskIsEnableDscp OBJECT-TYPE
        SYNTAX      EnabledStatus
        MAX-ACCESS  read-create
        STATUS      current
        DESCRIPTION "Indicates whether to check the IP DSCP against the packets.
                     The relative bitmask must be created before the ACE binds
                     to the interface in ingress direction.
                     This object cannot be configured when the status of the
                     entry, aclIngressIpMaskStatus, is active(1)."
        ::= { aclIngressIpMaskEntry 4 }

aclIngressIpMaskIsEnablePrecedence OBJECT-TYPE
        SYNTAX      EnabledStatus
        MAX-ACCESS  read-create
        STATUS      current
        DESCRIPTION "Indicates whether to check the IP precednce against the packets.
                     The relative bitmask must be created before the ACE
                    binds to the interface in ingress direction.
                     This object cannot be configured when the status of the
                     entry, aclIngressIpMaskStatus, is active(1)."
        ::= { aclIngressIpMaskEntry 5 }

aclIngressIpMaskIsEnableProtocol OBJECT-TYPE
        SYNTAX      EnabledStatus
        MAX-ACCESS  read-create
        STATUS      current
        DESCRIPTION "Indicates whether to check the IP protocol against the packets.
                     The relative bitmask must be created before the ACE
                        binds to the interface in ingress direction.
                     This object cannot be configured when the status of the
                     entry, aclIngressIpMaskStatus, is active(1)."
        ::= { aclIngressIpMaskEntry 6 }

aclIngressIpMaskSourceIpAddrBitmask OBJECT-TYPE
        SYNTAX      IpAddress
        MAX-ACCESS  read-create
        STATUS      current
        DESCRIPTION "Indicates the source IP bitmask to check against the packets,
                     The relative bitmask must be created before the ACE
                        binds to the interface in ingress direction.
                     This object cannot be configured when the status of the
                     entry, aclIngressIpMaskStatus, is active(1)."
        ::= { aclIngressIpMaskEntry 7 }

aclIngressIpMaskDestIpAddrBitmask OBJECT-TYPE
        SYNTAX      IpAddress
        MAX-ACCESS  read-create
        STATUS      current
        DESCRIPTION "Indicates the destination IP bitmask to check against the packets,
                     The relative bitmask must be created before the ACE
                        binds to the interface in ingress direction.
                     This object cannot be configured when the status of the
                     entry, aclIngressIpMaskStatus, is active(1)."
        ::= { aclIngressIpMaskEntry 8 }

aclIngressIpMaskSourcePortBitmask OBJECT-TYPE
        SYNTAX      Integer32 (0..'FFFF'h)
        MAX-ACCESS  read-create
        STATUS      current
        DESCRIPTION "Indicates the source port bitmask to check against the TCP/UDP packets,
                     The relative bitmask must be created before
                        the ACE binds to the interface in ingress direction.
                     This object cannot be configured when the status of the
                     entry, aclIngressIpMaskStatus, is active(1)."
        ::= { aclIngressIpMaskEntry 9 }

aclIngressIpMaskDestPortBitmask OBJECT-TYPE
        SYNTAX      Integer32 (0..'FFFF'h)
        MAX-ACCESS  read-create
        STATUS      current
        DESCRIPTION "Indicates the destination port bitmask to check against the TCP/UDP packets,
                     The relative bitmask must be created before
                        the ACE binds to the interface in ingress direction.
                     This object cannot be configured when the status of the
                     entry, aclIngressIpMaskStatus, is active(1)."
        ::= { aclIngressIpMaskEntry 10 }

aclIngressIpMaskControlCodeBitmask OBJECT-TYPE
        SYNTAX      Integer32 (0..63)
        MAX-ACCESS  read-create
        STATUS      current
        DESCRIPTION "Indicates the control code bitmask to check against the TCP packets,
                     The relative bitmask must be created before
                    the ACE binds to the interface in ingress direction.
                     This object cannot be configured when the status of the
                     entry, aclIngressIpMaskStatus, is active(1)."
        ::= { aclIngressIpMaskEntry 11 }

aclIngressIpMaskStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { aclIngressIpMaskEntry 12 }

--aclEgressIpMaskTable
aclEgressIpMaskTable OBJECT-TYPE
        SYNTAX      SEQUENCE OF AclEgressIpMaskEntry
        MAX-ACCESS  not-accessible
        STATUS      current
        DESCRIPTION "The conceptual table of aclEgressIpMaskEntry."
        ::= { aclMgt 5 }

aclEgressIpMaskEntry OBJECT-TYPE
        SYNTAX      AclEgressIpMaskEntry
        MAX-ACCESS  not-accessible
        STATUS      current
        DESCRIPTION "The conceptual row for aclEgressIpMaskTable."
        INDEX       { aclEgressIpMaskIndex }
        ::= { aclEgressIpMaskTable 1 }

AclEgressIpMaskEntry ::= SEQUENCE
{
    aclEgressIpMaskIndex                Integer32,
    aclEgressIpMaskPrecedence           Integer32,
    aclEgressIpMaskIsEnableTos          EnabledStatus,
    aclEgressIpMaskIsEnableDscp         EnabledStatus,
    aclEgressIpMaskIsEnablePrecedence   EnabledStatus,
    aclEgressIpMaskIsEnableProtocol     EnabledStatus,
    aclEgressIpMaskSourceIpAddrBitmask  IpAddress,
    aclEgressIpMaskDestIpAddrBitmask    IpAddress,
    aclEgressIpMaskSourcePortBitmask    Integer32,
    aclEgressIpMaskDestPortBitmask      Integer32,
    aclEgressIpMaskControlCodeBitmask   Integer32,
    aclEgressIpMaskStatus              RowStatus
}

aclEgressIpMaskIndex OBJECT-TYPE
        SYNTAX      Integer32 (1..16)
        MAX-ACCESS  not-accessible
        STATUS      current
         DESCRIPTION "The index of a mask entry within a mask table."
        ::= { aclEgressIpMaskEntry 1 }

aclEgressIpMaskPrecedence OBJECT-TYPE
        SYNTAX      Integer32 (0..16)
        MAX-ACCESS  read-only
        STATUS      current
        DESCRIPTION "The created precedence of an mask entry within the mask table."
        ::= { aclEgressIpMaskEntry 2 }

aclEgressIpMaskIsEnableTos OBJECT-TYPE
        SYNTAX      EnabledStatus
        MAX-ACCESS  read-create
        STATUS      current
        DESCRIPTION "Indicates whether to check the IP ToS facility against the packets.
                     The relative bitmask must be created before the
                     ACE binds to the interface in egress direction.
                     This object cannot be configured when the status of the
                     entry, aclEgressIpMaskStatus, is active(1)."
        ::= { aclEgressIpMaskEntry 3 }

aclEgressIpMaskIsEnableDscp OBJECT-TYPE
        SYNTAX      EnabledStatus
        MAX-ACCESS  read-create
        STATUS      current
        DESCRIPTION "Indicates whether to check the IP DSCP against the packets.
                     The relative bitmask must be created before the
                        ACE binds to the interface in egress direction.
                     This object cannot be configured when the status of the
                     entry, aclEgressIpMaskStatus, is active(1)."
        ::= { aclEgressIpMaskEntry 4 }

aclEgressIpMaskIsEnablePrecedence OBJECT-TYPE
        SYNTAX      EnabledStatus
        MAX-ACCESS  read-create
        STATUS      current
        DESCRIPTION "Indicates whether to check the IP precedence against the packets.
                     The relative bitmask must be created before the
                        ACE binds to the interface in egress direction.
                     This object cannot be configured when the status of the
                     entry, aclEgressIpMaskStatus, is active(1)."
        ::= { aclEgressIpMaskEntry 5 }

aclEgressIpMaskIsEnableProtocol OBJECT-TYPE
        SYNTAX      EnabledStatus
        MAX-ACCESS  read-create
        STATUS      current
         DESCRIPTION "Indicates whether to check the IP protocol against the packets.
                      The relative bitmask must be created before the ACE binds to
                        the interface in egress direction.
                      This object cannot be configured when the status of the
                      entry, aclEgressIpMaskStatus, is active(1)."
        ::= { aclEgressIpMaskEntry 6 }

aclEgressIpMaskSourceIpAddrBitmask OBJECT-TYPE
        SYNTAX      IpAddress
        MAX-ACCESS  read-create
        STATUS      current
        DESCRIPTION "Indicates the source IP bitmask to check against the packets.
                     The relative bitmask must be created before the
                        ACE binds to the interface in egress direction.
                     This object cannot be configured when the status of the
                     entry, aclEgressIpMaskStatus, is active(1)."
        ::= { aclEgressIpMaskEntry 7 }

aclEgressIpMaskDestIpAddrBitmask OBJECT-TYPE
        SYNTAX      IpAddress
        MAX-ACCESS  read-create
        STATUS      current
        DESCRIPTION "Indicates the destination IP bitmask to check against the packets.
                     The relative bitmask must be created before the
                        ACE binds to the interface in egress direction.
                     This object cannot be configured when the status of the
                     entry, aclEgressIpMaskStatus, is active(1)."
        ::= { aclEgressIpMaskEntry 8 }

aclEgressIpMaskSourcePortBitmask OBJECT-TYPE
        SYNTAX      Integer32 (0..'FFFF'h)
        MAX-ACCESS  read-create
        STATUS      current
        DESCRIPTION "Indicates the source port bitmask to check against the TCP/UDP packets.
                     The relative bitmask must be created before the
                        ACE binds to the interface in egress direction.
                     This object cannot be configured when the status of the
                     entry, aclEgressIpMaskStatus, is active(1)."
        ::= { aclEgressIpMaskEntry 9 }

aclEgressIpMaskDestPortBitmask OBJECT-TYPE
        SYNTAX      Integer32 (0..'FFFF'h)
        MAX-ACCESS  read-create
        STATUS      current
        DESCRIPTION "Indicates the destination port bitmask to check against the TCP/UDP packets.
                     The relative bitmask must be created before
                     the ACE binds to the interface in egress direction.
                     This object cannot be configured when the status of the
                     entry, aclEgressIpMaskStatus, is active(1)."
        ::= { aclEgressIpMaskEntry 10 }

aclEgressIpMaskControlCodeBitmask OBJECT-TYPE
        SYNTAX      Integer32 (0..63)
        MAX-ACCESS  read-create
        STATUS      current
        DESCRIPTION "Indicates the control code bitmask to check against the TCP packets.
                     The relative bitmask must be created before the
                        ACE binds to the interface in egress direction.
                     This object cannot be configured when the status of the
                     entry, aclEgressIpMaskStatus, is active(1)."
        ::= { aclEgressIpMaskEntry 11 }

aclEgressIpMaskStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { aclEgressIpMaskEntry 12 }

--aclIngressMacMaskTable
aclIngressMacMaskTable OBJECT-TYPE
        SYNTAX      SEQUENCE OF AclIngressMacMaskEntry
        MAX-ACCESS  not-accessible
        STATUS      current
        DESCRIPTION "The conceptual table of aclIngressMacMaskEntry."
        ::= { aclMgt 6 }

aclIngressMacMaskEntry OBJECT-TYPE
        SYNTAX      AclIngressMacMaskEntry
        MAX-ACCESS  not-accessible
        STATUS      current
        DESCRIPTION "The conceptual row for aclIngressMacMaskTable."
        INDEX       { aclIngressMacMaskIndex }
        ::= { aclIngressMacMaskTable 1 }

AclIngressMacMaskEntry ::= SEQUENCE
{
    aclIngressMacMaskIndex Integer32,
    aclIngressMacMaskPrecedence Integer32,
    aclIngressMacMaskSourceMacAddrBitmask OCTET STRING,
    aclIngressMacMaskDestMacAddrBitmask OCTET STRING,
    aclIngressMacMaskVidBitmask Integer32,
    aclIngressMacMaskEtherTypeBitmask  Integer32,
    aclIngressMacMaskIsEnablePktformat EnabledStatus,
    aclIngressMacMaskStatus RowStatus
}

aclIngressMacMaskIndex OBJECT-TYPE
        SYNTAX      Integer32 (1..16)
        MAX-ACCESS  not-accessible
        STATUS      current
        DESCRIPTION "The index of an mask entry within an ingress mask table."
        ::= { aclIngressMacMaskEntry 1 }

aclIngressMacMaskPrecedence OBJECT-TYPE
        SYNTAX      Integer32 (0..16)
        MAX-ACCESS  read-only
        STATUS      current
        DESCRIPTION "The created order of an mask entry within an ingress mask table."
        ::= { aclIngressMacMaskEntry 2 }

aclIngressMacMaskSourceMacAddrBitmask OBJECT-TYPE
        SYNTAX      OCTET STRING (SIZE (6))
        MAX-ACCESS  read-create
        STATUS      current
        DESCRIPTION "Indicates the source MAC bitmask to check against the packets.
                     The relative bitmask must be created before the ACE binds
                        to the interface in ingress direction.
                     This object cannot be configured when the status of the
                     entry, aclIngressMacMaskStatus, is active(1)."
        ::= { aclIngressMacMaskEntry 3 }

aclIngressMacMaskDestMacAddrBitmask OBJECT-TYPE
        SYNTAX      OCTET STRING (SIZE (6))
        MAX-ACCESS  read-create
        STATUS      current
        DESCRIPTION "Indicates the destination MAC bitmask to check against the packets.
                     The relative bitmask must be created before the ACE binds
                        to the interface in ingress direction.
                     This object cannot be configured when the status of the
                     entry, aclIngressMacMaskStatus, is active(1)."
        ::= { aclIngressMacMaskEntry 4 }

aclIngressMacMaskVidBitmask OBJECT-TYPE
        SYNTAX      Integer32 (0..'0FFF'h)
        MAX-ACCESS  read-create
        STATUS      current
        DESCRIPTION "Indicates the vid bitmask to check against the packets,
                     The relative bitmask must be created before the ACE binds
                        to the interface in ingress direction.
                     This object cannot be configured when the status of the
                     entry, aclIngressMacMaskStatus, is active(1)."
        ::= { aclIngressMacMaskEntry 5 }

aclIngressMacMaskEtherTypeBitmask OBJECT-TYPE
        SYNTAX      Integer32 (0..'FFFF'h)
        MAX-ACCESS  read-create
        STATUS      current
        DESCRIPTION "Indicates the ethertype bitmask to check against the packets.
                     The relative bitmask must be created before the ACE binds
                        to the interface in ingress direction.
                     This object cannot be configured when the status of the
                     entry, aclIngressMacMaskStatus, is active(1)."
        ::= { aclIngressMacMaskEntry 6 }

aclIngressMacMaskIsEnablePktformat OBJECT-TYPE
        SYNTAX      EnabledStatus
        MAX-ACCESS  read-create
        STATUS      current
         DESCRIPTION "Indicates whether to check the packet format against the packets.
                      The relative bitmask must be created before the ACE binds
                        to the interface in ingress direction.
                      This object cannot be configured when the status of the
                      entry, aclIngressMacMaskStatus, is active(1)."
        ::= { aclIngressMacMaskEntry 7 }

aclIngressMacMaskStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { aclIngressMacMaskEntry 8 }

--aclEgressMacMaskTable
aclEgressMacMaskTable OBJECT-TYPE
        SYNTAX      SEQUENCE OF AclEgressMacMaskEntry
        MAX-ACCESS  not-accessible
        STATUS      current
        DESCRIPTION "The conceptual table of aclEgressMacMaskEntry."
        ::= { aclMgt 7 }

aclEgressMacMaskEntry OBJECT-TYPE
        SYNTAX      AclEgressMacMaskEntry
        MAX-ACCESS  not-accessible
        STATUS      current
        DESCRIPTION "The conceptual row for aclEgressMacMaskTable."
        INDEX       { aclEgressMacMaskIndex }
        ::= { aclEgressMacMaskTable 1 }

AclEgressMacMaskEntry ::= SEQUENCE
{
    aclEgressMacMaskIndex                   Integer32,
    aclEgressMacMaskPrecedence              Integer32,
    aclEgressMacMaskSourceMacAddrBitmask    OCTET STRING,
    aclEgressMacMaskDestMacAddrBitmask      OCTET STRING,
    aclEgressMacMaskVidBitmask              Integer32,
    aclEgressMacMaskEtherTypeBitmask        Integer32,
    aclEgressMacMaskIsEnablePktformat       EnabledStatus,
    aclEgressMacMaskStatus                  RowStatus
}

aclEgressMacMaskIndex OBJECT-TYPE
        SYNTAX      Integer32 (1..16)
        MAX-ACCESS  not-accessible
        STATUS      current
        DESCRIPTION "The index of a mask entry within an egress mask table."
        ::= { aclEgressMacMaskEntry 1 }

aclEgressMacMaskPrecedence OBJECT-TYPE
        SYNTAX      Integer32 (0..16)
        MAX-ACCESS  read-only
        STATUS      current
        DESCRIPTION "The created precedence of a mask entry within an egress mask table."
        ::= { aclEgressMacMaskEntry 2 }

aclEgressMacMaskSourceMacAddrBitmask OBJECT-TYPE
        SYNTAX      OCTET STRING (SIZE (6))
        MAX-ACCESS  read-create
        STATUS      current
        DESCRIPTION "Indicates the source MAC bitmask to check against the packets,
                     The relative bitmask must be created before the ACE binds
                        to the interface in ingress direction.
                     This object cannot be configured when the status of the
                     entry, aclEgressMacMaskStatus, is active(1)."
        ::= { aclEgressMacMaskEntry 3 }

aclEgressMacMaskDestMacAddrBitmask OBJECT-TYPE
        SYNTAX      OCTET STRING (SIZE (6))
        MAX-ACCESS  read-create
        STATUS      current
        DESCRIPTION "Indicates the destination MAC bitmask to check against the packets,
                     The relative bitmask must be created before the ACE binds
                        to the interface in ingress direction.
                     This object cannot be configured when the status of the
                     entry, aclEgressMacMaskStatus, is active(1)."
        ::= { aclEgressMacMaskEntry 4 }

aclEgressMacMaskVidBitmask OBJECT-TYPE
        SYNTAX      Integer32 (0..'0FFF'h)
        MAX-ACCESS  read-create
        STATUS      current
        DESCRIPTION "Indicates the vid bitmask to check against the packets.
                     The relative bitmask must be created before the ACE binds
                        to the interface in ingress direction.
                     This object cannot be configured when the status of the
                     entry, aclEgressMacMaskStatus, is active(1)."
        ::= { aclEgressMacMaskEntry 5 }

aclEgressMacMaskEtherTypeBitmask OBJECT-TYPE
        SYNTAX      Integer32 (0..'FFFF'h)
        MAX-ACCESS  read-create
        STATUS      current
        DESCRIPTION "Indicates the ethertype bitmask to check against the packets.
                     The relative bitmask must be created before the ACE binds
                        to the interface in ingress direction.
                     This object cannot be configured when the status of the
                     entry, aclEgressMacMaskStatus, is active(1)."
        ::= { aclEgressMacMaskEntry 6 }

aclEgressMacMaskIsEnablePktformat OBJECT-TYPE
        SYNTAX      EnabledStatus
        MAX-ACCESS  read-create
        STATUS      current
        DESCRIPTION "Indicates whether to check the packet format against the packets.
                     The relative bitmask must be created before the ACE binds
                        to the interface in ingress direction.
                     This object cannot be configured when the status of the
                     entry, aclEgressMacMaskStatus, is active(1)."
        ::= { aclEgressMacMaskEntry 7 }

aclEgressMacMaskStatus OBJECT-TYPE
        SYNTAX      RowStatus
        MAX-ACCESS  read-create
        STATUS      current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
        ::= { aclEgressMacMaskEntry 8 }

--aclIpTable
aclIpTable OBJECT-TYPE
        SYNTAX      SEQUENCE OF AclIpEntry
        MAX-ACCESS  not-accessible
        STATUS      current
        DESCRIPTION "The conceptual table of all of aclIpEntry."
        ::= { aclMgt 8 }

aclIpEntry OBJECT-TYPE
        SYNTAX      AclIpEntry
        MAX-ACCESS  not-accessible
        STATUS      current
        DESCRIPTION "The conceptual row for aclIpTable."
        INDEX       { aclIpAclName }
        ::= { aclIpTable 1 }

AclIpEntry ::= SEQUENCE
{
    aclIpAclName   DisplayString
}

aclIpAclName OBJECT-TYPE
        SYNTAX      DisplayString(SIZE(1..16))
        MAX-ACCESS  read-only
        STATUS      current
        DESCRIPTION "The name of an ACL. Within a feature, a unique
                    name is used to identify
                    the list to which the entry belongs in the device."
        ::= { aclIpEntry 1 }

--aclMacTable
aclMacTable OBJECT-TYPE
        SYNTAX      SEQUENCE OF AclMacEntry
        MAX-ACCESS  not-accessible
        STATUS      current
        DESCRIPTION "The conceptual table of all of aclMacEntry."
        ::= { aclMgt 9 }

aclMacEntry OBJECT-TYPE
        SYNTAX      AclMacEntry
        MAX-ACCESS  not-accessible
        STATUS      current
        DESCRIPTION "The conceptual row for aclMacTable."
        INDEX       { aclMacAclName }
        ::= { aclMacTable 1 }

AclMacEntry ::= SEQUENCE
{
    aclMacAclName   DisplayString
}

aclMacAclName OBJECT-TYPE
        SYNTAX      DisplayString(SIZE(1..16))
        MAX-ACCESS  read-only
        STATUS      current
        DESCRIPTION "The name of an ACL. Within a feature, a unique
                    name is used to identify
                    the list to which the entry belongs in the device."
        ::= { aclMacEntry 1 }

-- bcastFilterMgt

bcastFilterTable OBJECT-TYPE
        SYNTAX      SEQUENCE OF BcastFilterEntry
        MAX-ACCESS  not-accessible
        STATUS      current
        DESCRIPTION "The conceptual table of bcastFilterEntry."
        ::= { bcastFilterMgt 1 }

bcastFilterEntry OBJECT-TYPE
        SYNTAX      BcastFilterEntry
        MAX-ACCESS  not-accessible
        STATUS      current
        DESCRIPTION "The conceptual row for bcastFilterTable."
        INDEX       { bcastFilterPortIndex }
        ::= { bcastFilterTable 1 }

BcastFilterEntry ::= SEQUENCE
{
    bcastFilterPortIndex                Integer32,
    bcastFilterOutputStatus             EnabledStatus
}

bcastFilterPortIndex OBJECT-TYPE
        SYNTAX      Integer32
        MAX-ACCESS  not-accessible
        STATUS      current
        DESCRIPTION "Specifies the interface number which turns on/off
                     the broadcast egressf filtering function."
        ::= { bcastFilterEntry 1 }

bcastFilterOutputStatus OBJECT-TYPE
        SYNTAX      EnabledStatus
        MAX-ACCESS  read-write
        STATUS      current
        DESCRIPTION "Turn on/off the broadcast egress filtering function."
        ::= { bcastFilterEntry 3 }

--
-- ipFilterMgt
--

--ipFilterSnmpTable
ipFilterSnmpTable  OBJECT-TYPE
    SYNTAX     SEQUENCE OF IpFilterSnmpEntry
    MAX-ACCESS not-accessible
    STATUS     current
    DESCRIPTION
        "A list of IP address entries."
    ::= { ipFilterMgt 1 }

ipFilterSnmpEntry  OBJECT-TYPE
    SYNTAX     IpFilterSnmpEntry
    MAX-ACCESS not-accessible
    STATUS     current
    DESCRIPTION
        "This entry includes an IP address range which the system
         will allow to connect to this device through SNMP."
    INDEX { ipFilterSnmpStartAddress }
    ::= { ipFilterSnmpTable 1 }

IpFilterSnmpEntry ::= SEQUENCE {
    ipFilterSnmpStartAddress        IpAddress,
    ipFilterSnmpEndAddress          IpAddress,
    ipFilterSnmpStatus              ValidStatus
    }

ipFilterSnmpStartAddress OBJECT-TYPE
        SYNTAX      IpAddress
        MAX-ACCESS  not-accessible
        STATUS      current
        DESCRIPTION "The start IP address."
        ::= { ipFilterSnmpEntry 1 }

ipFilterSnmpEndAddress OBJECT-TYPE
        SYNTAX      IpAddress
        MAX-ACCESS  read-create
        STATUS      current
        DESCRIPTION "The end IP address."
        ::= { ipFilterSnmpEntry 2 }

ipFilterSnmpStatus OBJECT-TYPE
        SYNTAX      ValidStatus
        MAX-ACCESS  read-create
        STATUS      current
        DESCRIPTION "Setting this to valid(1) creates an entry.
                     Setting this to invalid(2) destroys an entry."
        ::= { ipFilterSnmpEntry 3 }

--ipFilterHTTPTable
ipFilterHTTPTable  OBJECT-TYPE
    SYNTAX     SEQUENCE OF IpFilterHTTPEntry
    MAX-ACCESS not-accessible
    STATUS     current
    DESCRIPTION
        "A list of IP address entries."
    ::= { ipFilterMgt 2 }

ipFilterHTTPEntry  OBJECT-TYPE
    SYNTAX     IpFilterHTTPEntry
    MAX-ACCESS not-accessible
    STATUS     current
    DESCRIPTION
        "This entry includes an IP address range which the system
         will allow to connect to this device through SNMP."
    INDEX { ipFilterHTTPStartAddress }
    ::= { ipFilterHTTPTable 1 }

IpFilterHTTPEntry ::= SEQUENCE {
    ipFilterHTTPStartAddress        IpAddress,
    ipFilterHTTPEndAddress          IpAddress,
    ipFilterHTTPStatus              ValidStatus
}

ipFilterHTTPStartAddress OBJECT-TYPE
        SYNTAX      IpAddress
        MAX-ACCESS  not-accessible
        STATUS      current
        DESCRIPTION "The start IP address."
        ::= { ipFilterHTTPEntry 1 }

ipFilterHTTPEndAddress OBJECT-TYPE
        SYNTAX      IpAddress
        MAX-ACCESS  read-create
        STATUS      current
        DESCRIPTION "The end IP address."
        ::= { ipFilterHTTPEntry 2 }

ipFilterHTTPStatus OBJECT-TYPE
        SYNTAX      ValidStatus
        MAX-ACCESS  read-create
        STATUS      current
        DESCRIPTION "Setting this to valid(1) creates an entry.
                     Setting this to invalid(2) destroys an entry."
        ::= { ipFilterHTTPEntry 3 }

--ipFilterTelnetTable
ipFilterTelnetTable  OBJECT-TYPE
    SYNTAX     SEQUENCE OF IpFilterTelnetEntry
    MAX-ACCESS not-accessible
    STATUS     current
    DESCRIPTION
        "A list of IP address entries."
    ::= { ipFilterMgt 3 }

ipFilterTelnetEntry  OBJECT-TYPE
    SYNTAX     IpFilterTelnetEntry
    MAX-ACCESS not-accessible
    STATUS     current
    DESCRIPTION
        "This entry includes an IP address range which the system
         will allow them to connect to this device through SNMP."
    INDEX { ipFilterTelnetStartAddress }
    ::= { ipFilterTelnetTable 1 }

IpFilterTelnetEntry ::= SEQUENCE {
    ipFilterTelnetStartAddress        IpAddress,
    ipFilterTelnetEndAddress          IpAddress,
    ipFilterTelnetStatus              ValidStatus
}

ipFilterTelnetStartAddress OBJECT-TYPE
        SYNTAX      IpAddress
        MAX-ACCESS  not-accessible
        STATUS      current
        DESCRIPTION "The start IP address."
        ::= { ipFilterTelnetEntry 1 }

ipFilterTelnetEndAddress OBJECT-TYPE
        SYNTAX      IpAddress
        MAX-ACCESS  read-create
        STATUS      current
        DESCRIPTION "The end IP address."
        ::= { ipFilterTelnetEntry 2 }

ipFilterTelnetStatus OBJECT-TYPE
        SYNTAX      ValidStatus
        MAX-ACCESS  read-create
        STATUS      current
        DESCRIPTION "Setting this to valid(1) creates an entry.
                     Setting this to invalid(2) destroys an entry."
        ::= { ipFilterTelnetEntry 3 }

--ipFilterHttpsTable
ipFilterHttpsTable  OBJECT-TYPE
    SYNTAX     SEQUENCE OF IpFilterHttpsEntry
    MAX-ACCESS not-accessible
    STATUS     current
    DESCRIPTION
        "A list of IP address entries."
    ::= { ipFilterMgt 4 }

ipFilterHttpsEntry  OBJECT-TYPE
    SYNTAX     IpFilterHttpsEntry
    MAX-ACCESS not-accessible
    STATUS     current
    DESCRIPTION
        "This entry includes an IP address range which the system
         will allow to connect to this device through HTTPS"
    INDEX { ipFilterHttpsStartAddress }
    ::= { ipFilterHttpsTable 1 }

IpFilterHttpsEntry ::= SEQUENCE {
    ipFilterHttpsStartAddress        IpAddress,
    ipFilterHttpsEndAddress          IpAddress,
    ipFilterHttpsStatus              ValidStatus
    }

ipFilterHttpsStartAddress OBJECT-TYPE
        SYNTAX      IpAddress
        MAX-ACCESS  not-accessible
        STATUS      current
        DESCRIPTION "The start IP address."
        ::= { ipFilterHttpsEntry 1 }

ipFilterHttpsEndAddress OBJECT-TYPE
        SYNTAX      IpAddress
        MAX-ACCESS  read-create
        STATUS      current
        DESCRIPTION "The end IP address."
        ::= { ipFilterHttpsEntry 2 }

ipFilterHttpsStatus OBJECT-TYPE
        SYNTAX      ValidStatus
        MAX-ACCESS  read-create
        STATUS      current
        DESCRIPTION "Setting this to valid(1) creates an entry.
                     Setting this to invalid(2) destroys an entry."
        ::= { ipFilterHttpsEntry 3 }

--ipFilterSshTable
ipFilterSshTable  OBJECT-TYPE
    SYNTAX     SEQUENCE OF IpFilterSshEntry
    MAX-ACCESS not-accessible
    STATUS     current
    DESCRIPTION
        "A list of IP address entries."
    ::= { ipFilterMgt 5 }

ipFilterSshEntry  OBJECT-TYPE
    SYNTAX     IpFilterSshEntry
    MAX-ACCESS not-accessible
    STATUS     current
    DESCRIPTION
        "This entry includes an IP address range which the system
         will allow to connect to this device through SSH."
    INDEX { ipFilterSshStartAddress }
    ::= { ipFilterSshTable 1 }

IpFilterSshEntry ::= SEQUENCE {
    ipFilterSshStartAddress        IpAddress,
    ipFilterSshEndAddress          IpAddress,
    ipFilterSshStatus              ValidStatus
    }

ipFilterSshStartAddress OBJECT-TYPE
        SYNTAX      IpAddress
        MAX-ACCESS  not-accessible
        STATUS      current
        DESCRIPTION "The start IP address."
        ::= { ipFilterSshEntry 1 }

ipFilterSshEndAddress OBJECT-TYPE
        SYNTAX      IpAddress
        MAX-ACCESS  read-create
        STATUS      current
        DESCRIPTION "The end IP address."
        ::= { ipFilterSshEntry 2 }

ipFilterSshStatus OBJECT-TYPE
        SYNTAX      ValidStatus
        MAX-ACCESS  read-create
        STATUS      current
        DESCRIPTION "Setting this to valid(1) creates an entry.
                     Setting this to invalid(2) destroys an entry."
        ::= { ipFilterSshEntry 3 }

ipFilterSystemEnableStatus  OBJECT-TYPE
    SYNTAX     EnabledStatus
    MAX-ACCESS read-write
    STATUS     current
    DESCRIPTION
        "This enables Management IP Filter function for
         the whole system. If this is enabled(1), then the filtering
         for each specific protocol depends on its individual
         status. If this is disabled(2), then the filtering
         for all protocols is turned off."
    ::= { ipFilterMgt 6 }

--ipFilterSnmpSubnetTable
ipFilterSnmpSubnetTable  OBJECT-TYPE
    SYNTAX     SEQUENCE OF IpFilterSnmpSubnetEntry
    MAX-ACCESS not-accessible
    STATUS     current
    DESCRIPTION
        "A list of subnet entries."
    ::= { ipFilterMgt 7 }

ipFilterSnmpSubnetEntry  OBJECT-TYPE
    SYNTAX     IpFilterSnmpSubnetEntry
    MAX-ACCESS not-accessible
    STATUS     current
    DESCRIPTION
        "This entry includes a subnet which the system
         will allow to connect to this device through SNMP."
    INDEX { ipFilterSnmpSubnetAddress,
            ipFilterSnmpSubnetMask }
    ::= { ipFilterSnmpSubnetTable 1 }

IpFilterSnmpSubnetEntry ::= SEQUENCE {
    ipFilterSnmpSubnetAddress        IpAddress,
    ipFilterSnmpSubnetMask           IpAddress,
    ipFilterSnmpSubnetStatus         ValidStatus
    }

ipFilterSnmpSubnetAddress OBJECT-TYPE
    SYNTAX      IpAddress
    MAX-ACCESS  not-accessible
    STATUS      current
    DESCRIPTION
        "The subnet IP address."
    ::= { ipFilterSnmpSubnetEntry 1 }

ipFilterSnmpSubnetMask OBJECT-TYPE
    SYNTAX      IpAddress
    MAX-ACCESS  not-accessible
    STATUS      current
    DESCRIPTION
        "The subnet mask."
    ::= { ipFilterSnmpSubnetEntry 2 }

ipFilterSnmpSubnetStatus OBJECT-TYPE
   SYNTAX      ValidStatus
   MAX-ACCESS  read-create
   STATUS      current
   DESCRIPTION
       "Setting this to valid(1) creates an entry.
        Setting this to invalid(2) destroys an entry."
   ::= { ipFilterSnmpSubnetEntry 3 }

--ipFilterHttpSubnetTable
ipFilterHttpSubnetTable  OBJECT-TYPE
    SYNTAX     SEQUENCE OF IpFilterHttpSubnetEntry
    MAX-ACCESS not-accessible
    STATUS     current
    DESCRIPTION
        "A list of subnet entries."
    ::= { ipFilterMgt 8 }

ipFilterHttpSubnetEntry  OBJECT-TYPE
    SYNTAX     IpFilterHttpSubnetEntry
    MAX-ACCESS not-accessible
    STATUS     current
    DESCRIPTION
        "This entry includes a subnet which the system
         will allow to connect to this device through HTTP."
    INDEX { ipFilterHttpSubnetAddress,
            ipFilterHttpSubnetMask }
    ::= { ipFilterHttpSubnetTable 1 }

IpFilterHttpSubnetEntry ::= SEQUENCE {
    ipFilterHttpSubnetAddress        IpAddress,
    ipFilterHttpSubnetMask           IpAddress,
    ipFilterHttpSubnetStatus         ValidStatus
    }

ipFilterHttpSubnetAddress OBJECT-TYPE
    SYNTAX      IpAddress
    MAX-ACCESS  not-accessible
    STATUS      current
    DESCRIPTION
        "The subnet IP address."
    ::= { ipFilterHttpSubnetEntry 1 }

ipFilterHttpSubnetMask OBJECT-TYPE
    SYNTAX      IpAddress
    MAX-ACCESS  not-accessible
    STATUS      current
    DESCRIPTION
        "The subnet mask."
    ::= { ipFilterHttpSubnetEntry 2 }

ipFilterHttpSubnetStatus OBJECT-TYPE
   SYNTAX      ValidStatus
   MAX-ACCESS  read-create
   STATUS      current
   DESCRIPTION
       "Setting this to valid(1) creates an entry.
        Setting this to invalid(2) destroys an entry."
   ::= { ipFilterHttpSubnetEntry 3 }

--ipFilterTelnetSubnetTable
ipFilterTelnetSubnetTable  OBJECT-TYPE
    SYNTAX     SEQUENCE OF IpFilterTelnetSubnetEntry
    MAX-ACCESS not-accessible
    STATUS     current
    DESCRIPTION
        "A list of subnet entries."
    ::= { ipFilterMgt 9 }

ipFilterTelnetSubnetEntry  OBJECT-TYPE
    SYNTAX     IpFilterTelnetSubnetEntry
    MAX-ACCESS not-accessible
    STATUS     current
    DESCRIPTION
        "This entry includes a subnet which the system
         will allow to connect to this device through TELNET."
    INDEX { ipFilterTelnetSubnetAddress,
            ipFilterTelnetSubnetMask }
    ::= { ipFilterTelnetSubnetTable 1 }

IpFilterTelnetSubnetEntry ::= SEQUENCE {
    ipFilterTelnetSubnetAddress        IpAddress,
    ipFilterTelnetSubnetMask           IpAddress,
    ipFilterTelnetSubnetStatus         ValidStatus
    }

ipFilterTelnetSubnetAddress OBJECT-TYPE
    SYNTAX      IpAddress
    MAX-ACCESS  not-accessible
    STATUS      current
    DESCRIPTION
        "The subnet IP address."
    ::= { ipFilterTelnetSubnetEntry 1 }

ipFilterTelnetSubnetMask OBJECT-TYPE
    SYNTAX      IpAddress
    MAX-ACCESS  not-accessible
    STATUS      current
    DESCRIPTION
        "The subnet mask."
    ::= { ipFilterTelnetSubnetEntry 2 }

ipFilterTelnetSubnetStatus OBJECT-TYPE
    SYNTAX      ValidStatus
    MAX-ACCESS  read-create
    STATUS      current
    DESCRIPTION
        "Setting this to valid(1) creates an entry.
         Setting this to invalid(2) destroys an entry."
    ::= { ipFilterTelnetSubnetEntry 3 }

--ipFilterHttpsSubnetTable
ipFilterHttpsSubnetTable  OBJECT-TYPE
    SYNTAX     SEQUENCE OF IpFilterHttpsSubnetEntry
    MAX-ACCESS not-accessible
    STATUS     current
    DESCRIPTION
        "A list of subnet entries."
    ::= { ipFilterMgt 10 }

ipFilterHttpsSubnetEntry  OBJECT-TYPE
    SYNTAX     IpFilterHttpsSubnetEntry
    MAX-ACCESS not-accessible
    STATUS     current
    DESCRIPTION
        "This entry includes a subnet which the system
         will allow to connect to this device through HTTPS."
    INDEX { ipFilterHttpsSubnetAddress,
            ipFilterHttpsSubnetMask }
    ::= { ipFilterHttpsSubnetTable 1 }

IpFilterHttpsSubnetEntry ::= SEQUENCE {
    ipFilterHttpsSubnetAddress        IpAddress,
    ipFilterHttpsSubnetMask           IpAddress,
    ipFilterHttpsSubnetStatus         ValidStatus
    }

ipFilterHttpsSubnetAddress OBJECT-TYPE
    SYNTAX      IpAddress
    MAX-ACCESS  not-accessible
    STATUS      current
    DESCRIPTION
        "The subnet IP address."
    ::= { ipFilterHttpsSubnetEntry 1 }

ipFilterHttpsSubnetMask OBJECT-TYPE
    SYNTAX      IpAddress
    MAX-ACCESS  not-accessible
    STATUS      current
    DESCRIPTION
        "The subnet mask."
    ::= { ipFilterHttpsSubnetEntry 2 }

ipFilterHttpsSubnetStatus OBJECT-TYPE
   SYNTAX      ValidStatus
   MAX-ACCESS  read-create
   STATUS      current
   DESCRIPTION
       "Setting this to valid(1) creates an entry.
        Setting this to invalid(2) destroys an entry."
   ::= { ipFilterHttpsSubnetEntry 3 }

--ipFilterSshSubnetTable
ipFilterSshSubnetTable  OBJECT-TYPE
    SYNTAX     SEQUENCE OF IpFilterSshSubnetEntry
    MAX-ACCESS not-accessible
    STATUS     current
    DESCRIPTION
        "A list of subnet entries."
    ::= { ipFilterMgt 11 }

ipFilterSshSubnetEntry  OBJECT-TYPE
    SYNTAX     IpFilterSshSubnetEntry
    MAX-ACCESS not-accessible
    STATUS     current
    DESCRIPTION
        "This entry includes a subnet which the system
         will allow to connect to this device through SSH."
    INDEX { ipFilterSshSubnetAddress,
            ipFilterSshSubnetMask }
    ::= { ipFilterSshSubnetTable 1 }

IpFilterSshSubnetEntry ::= SEQUENCE {
    ipFilterSshSubnetAddress        IpAddress,
    ipFilterSshSubnetMask           IpAddress,
    ipFilterSshSubnetStatus         ValidStatus
    }

ipFilterSshSubnetAddress OBJECT-TYPE
    SYNTAX      IpAddress
    MAX-ACCESS  not-accessible
    STATUS      current
    DESCRIPTION
        "The subnet IP address."
    ::= { ipFilterSshSubnetEntry 1 }

ipFilterSshSubnetMask OBJECT-TYPE
    SYNTAX      IpAddress
    MAX-ACCESS  not-accessible
    STATUS      current
    DESCRIPTION
        "The subnet mask."
    ::= { ipFilterSshSubnetEntry 2 }

ipFilterSshSubnetStatus OBJECT-TYPE
   SYNTAX      ValidStatus
   MAX-ACCESS  read-create
   STATUS      current
   DESCRIPTION
       "Setting this to valid(1) creates an entry.
        Setting this to invalid(2) destroys an entry."
   ::= { ipFilterSshSubnetEntry 3 }

--
-- aaaMgt
--



--
--The aaaMethodTable is change to aaaAccountMethodTable in ES4548-08
--
--aaaAccountMethodTable OBJECT-TYPE
--        SYNTAX      SEQUENCE OF AaaAccountMethodEntry
--        MAX-ACCESS  not-accessible
--        STATUS      current
--        DESCRIPTION "Contains the settings needed for accounting."
--        ::= { aaaMgt 1 }
--
--aaaAccountMethodEntry OBJECT-TYPE
--        SYNTAX      AaaAccountMethodEntry
--        MAX-ACCESS  not-accessible
--        STATUS      current
--        DESCRIPTION "A conceptual row in the aaaAccountMethodTable."
--        INDEX      { aaaAccountMethodIndex }
--        ::= { aaaAccountMethodTable 1 }
--
--AaaAccountMethodEntry ::= SEQUENCE {
--        aaaAccountMethodIndex                  Integer32,
--        aaaAccountMethodName                   DisplayString,
--        aaaAccountMethodGroupName              DisplayString,
--        aaaAccountMethodMode                   INTEGER,
--        aaaAccountMethodStatus                 ValidStatus
--}
--
--aaaAccountMethodIndex OBJECT-TYPE
--        SYNTAX       Integer32
--        MAX-ACCESS   not-accessible
--        STATUS       current
--        DESCRIPTION  "Specifies the index for the entry."
--        ::= { aaaAccountMethodEntry 1 }
--
--aaaAccountMethodName OBJECT-TYPE
--        SYNTAX       DisplayString
--        MAX-ACCESS   read-create
--        STATUS       current
--        DESCRIPTION "Name for the method."
--        ::= { aaaAccountMethodEntry 2 }
--
--aaaAccountMethodGroupName OBJECT-TYPE
--        SYNTAX       DisplayString
--        MAX-ACCESS   read-create
--        STATUS       current
--        DESCRIPTION "Name for the server to use, pointing to aaaRadiusGroupName
--                     or aaaTacacsPlusGroupName."
--        ::= { aaaAccountMethodEntry 3 }
--
--aaaAccountMethodMode OBJECT-TYPE
--        SYNTAX      INTEGER
--                    {
--                       start-stop(1)
--                    }
--        MAX-ACCESS  read-create
--        STATUS      current
--        DESCRIPTION "start-stop(1),sends a 'start' accounting notice at the beginning of a process and
--        a 'stop' accounting notice at the end of a process. The 'start' accounting record
--        is sent in the background. The requested user process begins regardless of whether or not
--        the 'start' accounting notice was received by the accounting server."
--        ::= { aaaAccountMethodEntry 4 }
--
--aaaAccountMethodStatus OBJECT-TYPE
--        SYNTAX      ValidStatus
--        MAX-ACCESS  read-create
--        STATUS      current
--        DESCRIPTION "Set to 1 to initiate the aaaAccountMethodTable, 2 to destroy the table."
--        ::= { aaaAccountMethodEntry 5 }
--
--aaaAccountMethodClientType OBJECT-TYPE
--        SYNTAX      INTEGER
--                    {
--                       dot1x(1), exec(2)
--                    }
--        MAX-ACCESS  read-create
--        STATUS      current
--        DESCRIPTION "dot1x(1): Provide accounting service for dot1x activity;
--                     exec(2):  Provide accounting service for exec connection
--                     such as telnet, ssh or console"
--        ::= { aaaAccountMethodEntry 6 }

aaaMethodTable OBJECT-TYPE
        SYNTAX      SEQUENCE OF AaaMethodEntry
        MAX-ACCESS  not-accessible
        STATUS      current
        DESCRIPTION "Contains the settings needed for accounting."
        ::= { aaaMgt 1 }

aaaMethodEntry OBJECT-TYPE
        SYNTAX      AaaMethodEntry
        MAX-ACCESS  not-accessible
        STATUS      current
        DESCRIPTION "A conceptual row in the aaaMethodTable."
        INDEX      { aaaMethodIndex }
        ::= { aaaMethodTable 1 }

AaaMethodEntry ::= SEQUENCE {
        aaaMethodIndex                  Integer32,
        aaaMethodName                   DisplayString,
        aaaMethodGroupName              DisplayString,
        aaaMethodMode                   INTEGER,
        aaaMethodStatus                 ValidStatus,
        aaaMethodClientType             INTEGER,
        aaaMethodPrivilegeLevel         INTEGER
}

aaaMethodIndex OBJECT-TYPE
        SYNTAX       Integer32
        MAX-ACCESS   not-accessible
        STATUS       current
        DESCRIPTION  "Specifies the index for the entry."
        ::= { aaaMethodEntry 1 }

aaaMethodName OBJECT-TYPE
        SYNTAX       DisplayString(SIZE(1..255))
        MAX-ACCESS   read-create
        STATUS       current
        DESCRIPTION "Name for the method."
        ::= { aaaMethodEntry 2 }

aaaMethodGroupName OBJECT-TYPE
        SYNTAX       DisplayString(SIZE(1..255))
        MAX-ACCESS   read-create
        STATUS       current
        DESCRIPTION "Name for the server to use, pointing to aaaRadiusGroupName
                     or aaaTacacsPlusGroupName."
        ::= { aaaMethodEntry 3 }

aaaMethodMode OBJECT-TYPE
        SYNTAX      INTEGER
                    {
                       start-stop(1)
                    }
        MAX-ACCESS  read-create
        STATUS      current
        DESCRIPTION "start-stop(1),sends a 'start' accounting notice at the beginning of a process and
        a 'stop' accounting notice at the end of a process. The 'start' accounting record
        is sent in the background. The requested user process begins regardless of whether or not
        the 'start' accounting notice was received by the accounting server."
        ::= { aaaMethodEntry 4 }

aaaMethodStatus OBJECT-TYPE
        SYNTAX      ValidStatus
        MAX-ACCESS  read-create
        STATUS      current
        DESCRIPTION "Set to 1 to initiate the aaaMethodTable, 2 to destroy the table."
        ::= { aaaMethodEntry 5 }

aaaMethodClientType OBJECT-TYPE
        SYNTAX      INTEGER
                    {
                       dot1x(1), exec(2), commands(3)
                    }
        MAX-ACCESS  read-create
        STATUS      current
        DESCRIPTION "dot1x(1): Provides accounting service for 802.1x activity;
                     exec(2): Provides accounting service for EXEC connection
                     such as Telnet, SSH or console; commands(3): Provides
                     accounting service for command privileges."
        ::= { aaaMethodEntry 6 }

aaaMethodPrivilegeLevel OBJECT-TYPE
        SYNTAX       INTEGER (0..15)
        MAX-ACCESS   read-create
        STATUS       current
        DESCRIPTION  "Specifies the privilege level for the entry.
                      When aaaMethodClientType is in the mode of command(3),
                      the privilege level is enabled to be accessed."
        ::= { aaaMethodEntry 7 }

aaaRadiusGroupTable OBJECT-TYPE
        SYNTAX      SEQUENCE OF AaaRadiusGroupEntry
        MAX-ACCESS  not-accessible
        STATUS      current
        DESCRIPTION "Uses a subset of RADIUS servers for accounting as defined by the server group"
        ::= { aaaMgt 2 }

aaaRadiusGroupEntry OBJECT-TYPE
        SYNTAX      AaaRadiusGroupEntry
        MAX-ACCESS  not-accessible
        STATUS      current
        DESCRIPTION "A conceptual row of aaaRadiusGroupEntry."
        INDEX      { aaaRadiusGroupIndex }
        ::= { aaaRadiusGroupTable 1 }

AaaRadiusGroupEntry ::= SEQUENCE
{
        aaaRadiusGroupIndex          Integer32,
        aaaRadiusGroupServerBitMap   OCTET STRING,
        aaaRadiusGroupName           DisplayString,
        aaaRadiusGroupStatus         ValidStatus
}

aaaRadiusGroupIndex OBJECT-TYPE
        SYNTAX      Integer32
        MAX-ACCESS  not-accessible
        STATUS      current
        DESCRIPTION "Specifies the index for the entry."
        ::= { aaaRadiusGroupEntry 1 }

aaaRadiusGroupServerBitMap OBJECT-TYPE
        SYNTAX      OCTET STRING (SIZE (1))
        MAX-ACCESS  read-create
        STATUS      current
        DESCRIPTION "Identifies which RADIUS sever to use, each bit points to each radius server.
        80 (1000 0000) point to radius server 1, C0 (11000000) points to radius 1 and radius 2."
        ::= { aaaRadiusGroupEntry 2 }

aaaRadiusGroupName OBJECT-TYPE
        SYNTAX      DisplayString
        MAX-ACCESS  read-create
        STATUS      current
        DESCRIPTION "Uses a subset of servers for accounting as
        defined by the server group. The same name as aaaTacasPlusGroupName is not allowed."
        ::= { aaaRadiusGroupEntry 3 }

aaaRadiusGroupStatus OBJECT-TYPE
        SYNTAX      ValidStatus
        MAX-ACCESS  read-create
        STATUS      current
        DESCRIPTION "Set to 1 to initiate the aaaRadiusGroupTable, 2 to destroy the table."
        ::= { aaaRadiusGroupEntry 4 }

aaaTacacsPlusGroupTable OBJECT-TYPE
        SYNTAX      SEQUENCE OF AaaTacacsPlusGroupEntry
        MAX-ACCESS  not-accessible
        STATUS      current
        DESCRIPTION "Uses a subset of TACACS+ servers for accounting as defined by the server group"
        ::= { aaaMgt 3 }

aaaTacacsPlusGroupEntry OBJECT-TYPE
        SYNTAX      AaaTacacsPlusGroupEntry
        MAX-ACCESS  not-accessible
        STATUS      current
        DESCRIPTION "A conceptual row of aaaTacacsPlusGroupEntry."
        INDEX      { aaaTacacsPlusGroupIndex }
        ::= { aaaTacacsPlusGroupTable 1 }

AaaTacacsPlusGroupEntry ::= SEQUENCE
{
        aaaTacacsPlusGroupIndex          Integer32,
        aaaTacacsPlusGroupServerBitMap   OCTET STRING,
        aaaTacacsPlusGroupName           DisplayString,
        aaaTacacsPlusGroupStatus         ValidStatus
}

aaaTacacsPlusGroupIndex OBJECT-TYPE
        SYNTAX      Integer32
        MAX-ACCESS  not-accessible
        STATUS      current
        DESCRIPTION "Specifies the index for the entry."
        ::= { aaaTacacsPlusGroupEntry 1 }

aaaTacacsPlusGroupServerBitMap OBJECT-TYPE
        SYNTAX      OCTET STRING (SIZE (1))
        MAX-ACCESS  read-create
        STATUS      current
        DESCRIPTION "Identifies which TACACS+ sever to use."
        ::= { aaaTacacsPlusGroupEntry 2 }

aaaTacacsPlusGroupName OBJECT-TYPE
        SYNTAX      DisplayString
        MAX-ACCESS  read-create
        STATUS      current
        DESCRIPTION "Uses a subset of servers for accounting as
        defined by the server group. We can't have the same name as aaaRadiusGroupName"
        ::= { aaaTacacsPlusGroupEntry 3 }

aaaTacacsPlusGroupStatus OBJECT-TYPE
        SYNTAX      ValidStatus
        MAX-ACCESS  read-create
        STATUS      current
        DESCRIPTION "Set to 1 to initiate the aaaRadiusGroupTable, 2 to destroy the table."
        ::= { aaaTacacsPlusGroupEntry 4 }

aaaUpdate OBJECT-TYPE
        SYNTAX      Integer32 (1..2147483647)
        MAX-ACCESS  read-write
        STATUS      current
        DESCRIPTION "Specifies the periodic interim accounting records to be sent
        to the accounting server and periodic intervals to send accounting update records(in minutes)."
        ::= { aaaMgt 4 }

aaaAccountTable OBJECT-TYPE
        SYNTAX      SEQUENCE OF AaaAccountEntry
        MAX-ACCESS  not-accessible
        STATUS      current
        DESCRIPTION "Specifies an interface or a set of interfaces that the
                     accounting method list will be applied to."
        ::= { aaaMgt 5 }

aaaAccountEntry OBJECT-TYPE
        SYNTAX      AaaAccountEntry
        MAX-ACCESS  not-accessible
        STATUS      current
        DESCRIPTION "A conceptual row of aaaAccountTable."
        INDEX      { aaaAccountIfIndex }
        ::= { aaaAccountTable 1 }

AaaAccountEntry ::= SEQUENCE {
        aaaAccountIfIndex          Integer32,
        aaaAccountMethodName       DisplayString,
        aaaAccountProtocol         INTEGER,
        aaaAccountStatus           ValidStatus
}

aaaAccountIfIndex OBJECT-TYPE
        SYNTAX      Integer32
        MAX-ACCESS  not-accessible
        STATUS      current
        DESCRIPTION "Defined as the ifIndex"
        ::= { aaaAccountEntry 1 }

aaaAccountMethodName OBJECT-TYPE
        SYNTAX      DisplayString
        MAX-ACCESS  read-create
        STATUS      current
        DESCRIPTION "Specifies the name of the list of accounting methods to use.
        If no method name is specified, the system uses the default."
        ::= { aaaAccountEntry 2 }

aaaAccountProtocol OBJECT-TYPE
        SYNTAX      INTEGER
        MAX-ACCESS  read-only
        STATUS      current
        DESCRIPTION "Get the protocol type of a list method to know which server (RADIUS or TACACS+) is in use."
        ::= { aaaAccountEntry 3 }

aaaAccountStatus OBJECT-TYPE
        SYNTAX      ValidStatus
        MAX-ACCESS  read-create
        STATUS      current
        DESCRIPTION "Set to 1 to initiate the aaaRadiusGroupTable, 2 to destroy the table."
        ::= { aaaAccountEntry 4 }

aaaAuthMethodTable OBJECT-TYPE
        SYNTAX      SEQUENCE OF AaaAuthMethodEntry
        MAX-ACCESS  not-accessible
        STATUS      current
        DESCRIPTION "Contains the settings needed for authorization."
        ::= { aaaMgt 6 }

aaaAuthMethodEntry OBJECT-TYPE
        SYNTAX      AaaAuthMethodEntry
        MAX-ACCESS  not-accessible
        STATUS      current
        DESCRIPTION "A conceptual row in the aaaAuthMethodTable."
        INDEX      { aaaAuthMethodIndex }
        ::= { aaaAuthMethodTable 1 }

AaaAuthMethodEntry ::= SEQUENCE {
        aaaAuthMethodIndex                  Integer32,
        aaaAuthMethodName                   DisplayString,
        aaaAuthMethodGroupType              INTEGER,
        aaaAuthMethodGroupName              DisplayString,
        aaaAuthMethodStatus                 ValidStatus
}

aaaAuthMethodIndex OBJECT-TYPE
        SYNTAX       Integer32
        MAX-ACCESS   not-accessible
        STATUS       current
        DESCRIPTION  "Specifies the index for the entry."
        ::= { aaaAuthMethodEntry 1 }

aaaAuthMethodName OBJECT-TYPE
        SYNTAX       DisplayString
        MAX-ACCESS   read-create
        STATUS       current
        DESCRIPTION "Name for the method."
        ::= { aaaAuthMethodEntry 2 }

aaaAuthMethodGroupType OBJECT-TYPE
        SYNTAX      INTEGER
                    {
                       groupRadius(0), groupTacacsPlus(1),groupUnknown(2)
                    }
        MAX-ACCESS   read-only
        STATUS       current
        DESCRIPTION "Type of aaaAuthMethodGroupName.
                     groupRadius(0):The group of radius servers used for authorization;
                     groupTacacsPlus(1):The group of TACACS+ servers used  for authorization;
                     groupUnknown(2):Non-existent group"
        ::= { aaaAuthMethodEntry 3 }

aaaAuthMethodGroupName OBJECT-TYPE
        SYNTAX       DisplayString
        MAX-ACCESS   read-create
        STATUS       current
        DESCRIPTION "Name for the server to use, pointing to aaaRadiusGroupName
                     or aaaTacacsPlusGroupName."
        ::= { aaaAuthMethodEntry 4 }

aaaAuthMethodStatus OBJECT-TYPE
        SYNTAX      ValidStatus
        MAX-ACCESS  read-create
        STATUS      current
        DESCRIPTION "Set to 1 to initiate the aaaAuthMethodTable, 2 to destroy the table."
        ::= { aaaAuthMethodEntry 5 }

aaaAuthMethodClientType OBJECT-TYPE
        SYNTAX      INTEGER
                    {
                       dot1x(1), exec(2)
                    }
        MAX-ACCESS  read-create
        STATUS      current
        DESCRIPTION "dot1x(1): Provide authorization service for dot1x activity;
                     exec(2):  Provide authorization service for CLI management connection,
                     such as telnet, ssh or console"
        ::= { aaaAuthMethodEntry 6 }

aaaAuthExecTable OBJECT-TYPE
        SYNTAX      SEQUENCE OF AaaAuthExecEntry
        MAX-ACCESS  not-accessible
        STATUS      current
        DESCRIPTION "Specifies an interface or a set of interfaces that the
                     authorization method list will be applied to."
        ::= { aaaMgt 7 }

aaaAuthExecEntry OBJECT-TYPE
        SYNTAX      AaaAuthExecEntry
        MAX-ACCESS  not-accessible
        STATUS      current
        DESCRIPTION "A conceptual row of aaaAuthExecTable."
        INDEX      { aaaAuthExecIndex }
        ::= { aaaAuthExecTable 1 }

AaaAuthExecEntry ::= SEQUENCE {
        aaaAuthExecIndex            INTEGER,
        aaaAuthExecMethodName       DisplayString
}

aaaAuthExecIndex OBJECT-TYPE
        SYNTAX    INTEGER
                  {
                  console(1), vty(2)
                  }
        MAX-ACCESS  not-accessible
        STATUS      current
        DESCRIPTION "The method of accessing CLI management."
        ::= { aaaAuthExecEntry 1 }

aaaAuthExecMethodName OBJECT-TYPE
        SYNTAX      DisplayString
        MAX-ACCESS  read-create
        STATUS      current
        DESCRIPTION "Specifies the name of the list of authorization methods to use.
        If no method name is specified, the system uses the default."
        ::= { aaaAuthExecEntry 2 }

aaaCommandPrivilegesTable OBJECT-TYPE
        SYNTAX      SEQUENCE OF AaaCommandPrivilegesEntry
        MAX-ACCESS  not-accessible
        STATUS      current
        DESCRIPTION "Contains the settings needed for command privileges."
        ::= { aaaMgt 8 }

aaaCommandPrivilegesEntry OBJECT-TYPE
        SYNTAX      AaaCommandPrivilegesEntry
        MAX-ACCESS  not-accessible
        STATUS      current
        DESCRIPTION "A conceptual row in the aaaCommandPrivilegesTable."
        INDEX      { aaaCommandPrivilegesLevel, aaaCommandPrivilegesInterfaceIndex }
        ::= { aaaCommandPrivilegesTable 1 }

AaaCommandPrivilegesEntry ::= SEQUENCE {
        aaaCommandPrivilegesLevel            INTEGER,
        aaaCommandPrivilegesInterfaceIndex   INTEGER,
        aaaCommandPrivilegesMethodName       DisplayString
}

aaaCommandPrivilegesLevel OBJECT-TYPE
        SYNTAX       INTEGER (0..15)
        MAX-ACCESS   not-accessible
        STATUS       current
        DESCRIPTION  "Specifies the privilege level index for the entry."
        ::= { aaaCommandPrivilegesEntry 1 }

aaaCommandPrivilegesInterfaceIndex OBJECT-TYPE
        SYNTAX       INTEGER { console(1), vty(2) }
        MAX-ACCESS   not-accessible
        STATUS       current
        DESCRIPTION  "Specifies the interface index for the entry."
        ::= { aaaCommandPrivilegesEntry 2 }

aaaCommandPrivilegesMethodName OBJECT-TYPE
        SYNTAX       DisplayString(SIZE(1..255))
        MAX-ACCESS   read-create
        STATUS       current
        DESCRIPTION "Specifies the method name in the lists under
                     the mode of command privileges."
        ::= { aaaCommandPrivilegesEntry 3 }

aaaAccExecTable OBJECT-TYPE
        SYNTAX      SEQUENCE OF aaaAccExecEntry
        MAX-ACCESS  not-accessible
        STATUS      current
        DESCRIPTION "Specifies an interface or a set of interfaces that the
                     accounting method list will be applied to."
        ::= { aaaMgt 9 }

aaaAccExecEntry OBJECT-TYPE
        SYNTAX      aaaAccExecEntry
        MAX-ACCESS  not-accessible
        STATUS      current
        DESCRIPTION "A conceptual row of aaaAccExecTable."
        INDEX      { aaaAccExecIndex }
        ::= { aaaAccExecTable 1 }

aaaAccExecEntry ::= SEQUENCE {
        aaaAccExecIndex            INTEGER,
        aaaAccExecMethodName       DisplayString
}

aaaAccExecIndex OBJECT-TYPE
        SYNTAX    INTEGER
                  {
                  console(1), vty(2)
                  }
        MAX-ACCESS  not-accessible
        STATUS      current
        DESCRIPTION "The method of accessing CLI management."
        ::= { aaaAccExecEntry 1 }

aaaAccExecMethodName OBJECT-TYPE
        SYNTAX      DisplayString
        MAX-ACCESS  read-create
        STATUS      current
        DESCRIPTION "Specifies the name of the list of accounting methods to use.
        If no method name is specified, the system uses the default."
        ::= { aaaAccExecEntry 2 }

--
--userAuthMgt
--

userAuthAuthMethodSequence OBJECT-TYPE
        SYNTAX      OCTET STRING
        MAX-ACCESS  read-write
        STATUS      current
        DESCRIPTION "The authentication method sequence which applies for login.

                     Please refer to the TEXTUAL-CONVENTION AuthMethodType
                     for all supported authentication method types.

                     At least 1 method must be specified.
                     Duplicate methods are not acceptable in the current
                     implementation.
                     For example, [local, local, tacas] is an illegal setting.

                     Authentication methods are stored in an octet string in
                     sequence, the first byte representing the first method,
                     which has the highest priority, the second byte
                     representing the second method with the second highest
                     priority, and so on.

                     If not all method types are specified, the remaining
                     octets should be filled by zeros. However, any zero before a general
                     authentication method is illegal.

                     For example, for a total of 3 methods (local,radius,tacas),
                     we will have an octet string of length 3,
                     please see bleow:

                     authentication sequence        octet form
                     ============================================
                     local, radius, tacas           01 02 03
                     local, none, none              01 00 00
                     tacas, local, none             03 01 00
                     none, tacas, local             [illegal]
                     tacas, none, radius            [illegal]
                     tacas, local, local            [illegal(duplicate)]"
        ::= { userAuthMgt 1 }

userAuthEnableAuthMethodSequence OBJECT-TYPE
        SYNTAX      OCTET STRING
        MAX-ACCESS  read-write
        STATUS      current
        DESCRIPTION "The authentication method sequence which applies when switching
                     the EXEC mode from normal to privilege mode.

                     Please refer to the TEXTUAL-CONVENTION AuthMethodType
                     for all supported authentication method types.

                     At least 1 method must be specified.
                     Duplicate methods are not acceptable in the current
                     implementation.
                     For example, [local, local, tacas] is an illegal setting.

                     Authentication methods are stored in an octet string in
                     sequence, the first byte representing the first method,
                     which has the highest priority, the second byte
                     representing the second method with the second highest
                     priority, and so on.

                     If not all method types are specified, the remaining
                     octets should be filled by zeros. However, any zero before
                     a general authentication method is illegal.

                     For example, for a total of 3 methods (local,radius,tacas),
                     we will have an octet string of length 3,
                     please see bleow:

                     authentication sequence        octet form
                     ============================================
                     local, radius, tacas           01 02 03
                     local, none, none              01 00 00
                     tacas, local, none             03 01 00
                     none, tacas, local             [illegal]
                     tacas, none, radius            [illegal]
                     tacas, local, local            [illegal(duplicate)]"
        ::= { userAuthMgt 2 }

--
-- dot1xMgt
--

-- The extension table of dot1xAuthConfigTable

dot1xAuthConfigExtTable OBJECT-TYPE
        SYNTAX      SEQUENCE OF Dot1xAuthConfigExtEntry
        MAX-ACCESS  not-accessible
        STATUS      current
        DESCRIPTION "The extension table of dot1xAuthConfigTable."
        ::= { dot1xMgt 1 }

dot1xAuthConfigExtEntry OBJECT-TYPE
        SYNTAX      Dot1xAuthConfigExtEntry
        MAX-ACCESS  not-accessible
        STATUS      current
        DESCRIPTION "The entry of dot1xAuthConfigExtTable."
        AUGMENTS       { dot1xAuthConfigEntry }
        ::= { dot1xAuthConfigExtTable 1 }

Dot1xAuthConfigExtEntry ::= SEQUENCE
{
      dot1xAuthConfigExtOperMode              INTEGER,
      dot1xAuthConfigExtMultiHostMaxCnt       Integer32,
      dot1xAuthConfigExtPortIntrusionAction   INTEGER
}

dot1xAuthConfigExtOperMode OBJECT-TYPE
        SYNTAX      INTEGER
                    {
                        singleHost(1),
                        multiHost(2)
                    }
        MAX-ACCESS  read-write
        STATUS      current
        DESCRIPTION "The operation mode of dot1x port which allows host
                     connection to 802.1x-authorized ports."
        ::= { dot1xAuthConfigExtEntry 1 }

dot1xAuthConfigExtMultiHostMaxCnt OBJECT-TYPE
        SYNTAX      Integer32(1..1024)
        MAX-ACCESS  read-write
        STATUS      current
        DESCRIPTION "The maximum number of hosts when the
                     dot1xAuthConfigExtOperMode is multiHost(2). When the
                     operation Mode is singleHost(1), we can ignore this
                     variables."
        DEFVAL      { 5 }
        ::= { dot1xAuthConfigExtEntry 2  }

dot1xAuthConfigExtPortIntrusionAction      OBJECT-TYPE
    SYNTAX      INTEGER
                {
                    block-traffic(1),
                    guest-vlan(2)
                }
    MAX-ACCESS  read-write
    STATUS      current
    DESCRIPTION "Responses to intrusion when the authentication is failed.
                 block-traffic(1) means that to block traffic when the authentication is failed;
                 guest-vlan(2) means that to join to a guest VLAN when the authentication is failed."
    ::= { dot1xAuthConfigExtEntry 3 }

--
-- networkAccessMacFilterTable
--

networkAccessMacFilterTable   OBJECT-TYPE
    SYNTAX      SEQUENCE OF NetworkAccessMacFilterEntry
    MAX-ACCESS  not-accessible
    STATUS      current
    DESCRIPTION "Contains the settings for MAC filter."
	::= { networkAccessMgt  1}

networkAccessMacFilterEntry   OBJECT-TYPE
    SYNTAX      NetworkAccessMacFilterEntry
    MAX-ACCESS  not-accessible
    STATUS      current
    DESCRIPTION "A conceptual row in the networkAccessMacFilterTable."
    INDEX { networkAccessMacFilterID, networkAccessMacFilterMacAddress }
    ::= { networkAccessMacFilterTable  1 }

NetworkAccessMacFilterEntry ::= SEQUENCE
{
    networkAccessMacFilterID                INTEGER,
    networkAccessMacFilterMacAddress        MacAddress,
    networkAccessMacFilterStatus            INTEGER
}

networkAccessMacFilterID      OBJECT-TYPE
    SYNTAX      INTEGER
    MAX-ACCESS  not-accessible
    STATUS      current
    DESCRIPTION "Specifies the MAC filter ID"
    ::= { networkAccessMacFilterEntry 1 }

networkAccessMacFilterMacAddress      OBJECT-TYPE
    SYNTAX      MacAddress
    MAX-ACCESS  not-accessible
    STATUS      current
    DESCRIPTION "Specifies the Mac address to be filtered"
    ::= { networkAccessMacFilterEntry 2 }

networkAccessMacFilterStatus      OBJECT-TYPE
    SYNTAX      INTEGER
                {
                    valid(1),
                    invalid(2)
                }
    MAX-ACCESS  read-create
    STATUS      current
    DESCRIPTION "Sets valid(1) to create the entry in the networkAccessMacFilter table, and sets invalid(2) to destroy the entry."
    ::= { networkAccessMacFilterEntry 3 }

--
-- networkAccessPortTable
--

networkAccessPortTable   OBJECT-TYPE
    SYNTAX      SEQUENCE OF NetworkAccessPortEntry
    MAX-ACCESS  not-accessible
    STATUS      current
    DESCRIPTION "A table contains the information of network access about every port."
    ::= { networkAccessMgt 2 }

networkAccessPortEntry   OBJECT-TYPE
    SYNTAX      NetworkAccessPortEntry
    MAX-ACCESS  not-accessible
    STATUS      current
    DESCRIPTION "A conceptual row in the networkAccessPort table."
    INDEX { networkAccessPortPortIndex }
    ::= { networkAccessPortTable 1 }

NetworkAccessPortEntry ::= SEQUENCE
{
    networkAccessPortPortIndex        Integer32,
    networkAccessPortDynamicVlan      INTEGER,
    networkAccessPortMaxMacCount      INTEGER,
    networkAccessPortMode             INTEGER,
    networkAccessPortPortMacFilter    INTEGER,
    networkAccessPortGuestVlan        INTEGER,
    networkAccessPortIntrusionAction  INTEGER
}

networkAccessPortPortIndex      OBJECT-TYPE
    SYNTAX      Integer32
    MAX-ACCESS  not-accessible
    STATUS      current
    DESCRIPTION "The port and the trunk (excluding trunk members) interface of the
                 portTable. The interface identified by a particular value of this port
                 index is the same interface identified by the same value of
                 ifIndex in the IF-MIB."
    ::= { networkAccessPortEntry 1 }

networkAccessPortDynamicVlan      OBJECT-TYPE
    SYNTAX      EnabledStatus
    MAX-ACCESS  read-write
    STATUS      current
    DESCRIPTION "Sets enabled(1) to enable dynamic VLAN assigment and
                 sets disabled(2) to disable dynamic VLAN assigment."
    ::= { networkAccessPortEntry 2 }

networkAccessPortMaxMacCount      OBJECT-TYPE
    SYNTAX      INTEGER (0..1024)
    MAX-ACCESS  read-write
    STATUS      current
    DESCRIPTION "Specifies the maximum number of authenticated MAC address."
    ::= { networkAccessPortEntry 3 }

networkAccessPortMode      OBJECT-TYPE
    SYNTAX      EnabledStatus
    MAX-ACCESS  read-write
    STATUS      current
    DESCRIPTION "Specifies the secure port mode. enabled(1) means that Mac address
                 authentication is used and disabled(2) means that the authentication is disabled."
    ::= { networkAccessPortEntry 4 }

networkAccessPortPortMacFilter      OBJECT-TYPE
    SYNTAX      INTEGER (1..64)
    MAX-ACCESS  read-write
    STATUS      current
    DESCRIPTION "Specifies the mac-filter ID"
    ::= { networkAccessPortEntry 5 }

networkAccessPortGuestVlan      OBJECT-TYPE
    SYNTAX      INTEGER (0..4094)
    MAX-ACCESS  read-write
    STATUS      current
    DESCRIPTION "Specifies guest VLAN ID. Setting to 0 means disabled."
    ::= { networkAccessPortEntry 6 }

networkAccessPortIntrusionAction      OBJECT-TYPE
    SYNTAX      INTEGER
                {
                    block-traffic(1),
                    guest-vlan(2)
                }
    MAX-ACCESS  read-write
    STATUS      current
    DESCRIPTION "Responses to intrusion when the authentication is failed.
                 block-traffic(1) means that to block traffic when the authentication is failed;
                 guest-vlan(2) means that to join to a guest VLAN when the authentication is failed."
    ::= { networkAccessPortEntry 7 }

--
-- networkAccessClearMacAddressMgt
--

networkAccessClearMacAddressMgt           OBJECT IDENTIFIER ::= { networkAccessMgt 3 }

networkAccessClearMacAddressAttribute     OBJECT-TYPE
    SYNTAX      INTEGER
                {
                    all        (1),
                    static     (2),
                    dynamic    (3)
                }
    MAX-ACCESS  read-write
    STATUS      current
    DESCRIPTION "Attribute for clearing Mac address. Specifies the certain attribute
                 in Mac address table. all(1) indicates both reauthorized and learnt
                 secure MAC address; static(2) indicates reauthorized MAC address;
                 dynamic(3) indicates learnt secure MAC address."
    ::= { networkAccessClearMacAddressMgt 1 }

networkAccessClearMacAddressMacAddress     OBJECT-TYPE
    SYNTAX      MacAddress
    MAX-ACCESS  read-write
    STATUS      current
    DESCRIPTION "Specifies MAC address in the MAC address table for clearing
                 MAC address. '000000' represents that no MAC address is specified."

    ::= { networkAccessClearMacAddressMgt 2 }

networkAccessClearMacAddressPort     OBJECT-TYPE
    SYNTAX      Integer32
    MAX-ACCESS  read-write
    STATUS      current
    DESCRIPTION "The specifies port in the MAC address table for clearing MAC address.
                 '0' represents that no port is specified."

    ::= { networkAccessClearMacAddressMgt 3 }

networkAccessClearMacAddressAction     OBJECT-TYPE
    SYNTAX      INTEGER
                {
                    noclear     (1),
                    clear       (2)
                }
    MAX-ACCESS  read-write
    STATUS      current
    DESCRIPTION "Action for clearing MAC address . When setting this object to clear(2)
                           to begin the clearing MAC address operation, a particular MAC address
                           is cleared from the MAC address table. When the action is finshed whether
                           or not it is successful or no action is taken, the value of this object
                           is always noclear(1)."

    ::= { networkAccessClearMacAddressMgt 4 }

--
-- networkAccessMacAddressTable
--

networkAccessMacAddressTable   OBJECT-TYPE
    SYNTAX      SEQUENCE OF NetworkAccessMacAddressEntry
    MAX-ACCESS  not-accessible
	STATUS      current
	DESCRIPTION "Contains the information of network access MAC addresses."
	::= { networkAccessMgt  4}

networkAccessMacAddressEntry   OBJECT-TYPE
    SYNTAX      NetworkAccessMacAddressEntry
    MAX-ACCESS  not-accessible
    STATUS      current
    DESCRIPTION "A conceptual row in the networkAccessMacAddress table."
    INDEX { networkAccessMacAddressAddress, networkAccessMacAddressPort }
    ::= { networkAccessMacAddressTable  1 }

NetworkAccessMacAddressEntry ::= SEQUENCE
{
    networkAccessMacAddressAddress                       MacAddress,
    networkAccessMacAddressPort                          INTEGER,
    networkAccessMacAddressInetAddressType               InetAddressType,
    networkAccessMacAddressRadiusServerInetAddress       InetAddress,
    networkAccessMacAddressTime                          DisplayString,
    networkAccessMacAddressAttribute                     INTEGER
}

networkAccessMacAddressAddress      OBJECT-TYPE
    SYNTAX      MacAddress
    MAX-ACCESS  not-accessible
    STATUS      current
    DESCRIPTION "Specifies the authenticated MAC address."
    ::= { networkAccessMacAddressEntry 1 }

networkAccessMacAddressPort      OBJECT-TYPE
    SYNTAX      INTEGER
    MAX-ACCESS  not-accessible
    STATUS      current
    DESCRIPTION "Specifies the port of authenticated MAC address."
    ::= { networkAccessMacAddressEntry 2 }

networkAccessMacAddressInetAddressType   OBJECT-TYPE
    SYNTAX      InetAddressType
    MAX-ACCESS  read-only
    STATUS      current
    DESCRIPTION "This object indicates the type of IP address denoted in
                 networkAccessMacAddressRadiusServerInetAddress type."
    ::= { networkAccessMacAddressEntry 3 }

networkAccessMacAddressRadiusServerInetAddress      OBJECT-TYPE
    SYNTAX      InetAddress
    MAX-ACCESS  read-only
    STATUS      current
    DESCRIPTION "Displays the IP address of radius server that authenticates
                 the specified Mac address."
    ::= { networkAccessMacAddressEntry 4 }

networkAccessMacAddressTime      OBJECT-TYPE
    SYNTAX      DisplayString(SIZE(12))
    MAX-ACCESS  read-only
    STATUS      current
    DESCRIPTION "Displays the authentication time of the authenticated MAC address.
                 The following form is a text string; 'yyyy MMm DDd HHh MMm SSs'.
                 'yyyy' is a four-digit year. 'MM' is a month. A single-digit month is
                 preceded by a zero. 'DD' is the day of a month. A single-digit day
                 is preceded by the value zero. 'HH', 'MM' and 'SS' are hour,
                 minute, and second respectively. A single-digit hour, minute,
                 and second are preceded by a zero value. An example is:
                 '2001y 01m 01d 00h 04m 43s'."
    ::= { networkAccessMacAddressEntry 5 }

networkAccessMacAddressAttribute       OBJECT-TYPE
    SYNTAX      INTEGER
                {
                    static     (1),
                    dynamic    (2)
                }
    MAX-ACCESS  read-only
    STATUS      current
    DESCRIPTION "Displays the attribute of an authenticated MAC address.
                 static(1) indicates resauthorized secure MAC address.
                 dynamic(2) indicates learnt secure MAC address."
    ::= { networkAccessMacAddressEntry 6 }

macAuthReauthTime     OBJECT-TYPE
    SYNTAX      Integer32 (120..1000000)
    MAX-ACCESS  read-write
    STATUS      current
    DESCRIPTION "Specifies the reauthentication time period."
    ::= { macAuthMgt 1 }

--
-- macAuthPortTable
--

macAuthPortTable   OBJECT-TYPE
    SYNTAX      SEQUENCE OF MacAuthPortEntry
    MAX-ACCESS  not-accessible
    STATUS      current
    DESCRIPTION "Contains the settings for mac authentication of each port."
    ::= { macAuthMgt 2 }

macAuthPortEntry   OBJECT-TYPE
    SYNTAX      MacAuthPortEntry
    MAX-ACCESS  not-accessible
    STATUS      current
    DESCRIPTION "A conceptual row in the macAuthPort table."
    INDEX { macAuthPortIndex }
    ::= { macAuthPortTable  1 }

MacAuthPortEntry ::= SEQUENCE
{
    macAuthPortIndex              Integer32,
    macAuthPortMaxMacCount        INTEGER,
    macAuthPortIntrusionAction    INTEGER
}

macAuthPortIndex      OBJECT-TYPE
    SYNTAX      Integer32
    MAX-ACCESS  not-accessible
    STATUS      current
    DESCRIPTION "The port and the trunk (including trunk members) interface of the
                 port table. The interface identified by a particular value of this
                 index is the same interface identified by the same value
                 of ifIndex in the IF-MIB."
    ::= { macAuthPortEntry  1 }

macAuthPortMaxMacCount      OBJECT-TYPE
    SYNTAX      INTEGER (0..1024)
    MAX-ACCESS  read-write
    STATUS      current
    DESCRIPTION "Specifies the maximum number of authenticated MAC addresses for MAC authentication."
    ::= { macAuthPortEntry 2 }

macAuthPortIntrusionAction      OBJECT-TYPE
    SYNTAX      INTEGER
                {
                    block-traffic(1),
                    pass-traffic(2)
                }
    MAX-ACCESS  read-write
    STATUS      current
    DESCRIPTION "Responses to intrusion when the authentication is failed.
                 block-traffic(1) : denies network access to an unauthorized client;
                 pass-traffic(2) : allows unauthorized clients to the access network."
    ::= { macAuthPortEntry  3 }

-- ES3552MO-PoE-FLF-AA-00159
-- (New feature) Web-based Authentication feature
--
webAuthSystemAuthControl     OBJECT-TYPE
    SYNTAX      EnabledStatus
    MAX-ACCESS  read-write
    STATUS      current
    DESCRIPTION "Sets enabled(1) to enable WebAuth feature and
                 sets disabled(2) to disable WebAuth feature."
    ::= { webAuthMgt 1 }

webAuthLoginPageUrl     OBJECT-TYPE
    SYNTAX      DisplayString (SIZE(0..120))
    MAX-ACCESS  read-write
    STATUS      current
    DESCRIPTION "Specifies an external login page URL which hosted
                 login page. This external login page is used
                 to authenticate the users."
    ::= { webAuthMgt 2 }

webAuthLoginFailPageUrl     OBJECT-TYPE
    SYNTAX      DisplayString (SIZE(0..120))
    MAX-ACCESS  read-write
    STATUS      current
    DESCRIPTION "A login fail page URL is a web server's location which hosts the login fail page.
             For authenticated fail users, the login fail page is sent."
    ::= { webAuthMgt 3 }

webAuthLoginSuccessPageUrl     OBJECT-TYPE
    SYNTAX      DisplayString (SIZE(0..120))
    MAX-ACCESS  read-write
    STATUS      current
    DESCRIPTION "A login success page URL is a web
                 server's location which hosts login success page. For
                 authenticated success users, a login success page
                 is sent when original link is not expected."
    ::= { webAuthMgt 4 }

webAuthSessionTimeout     OBJECT-TYPE
    SYNTAX      INTEGER (300..3600)
    MAX-ACCESS  read-write
    STATUS      current
    DESCRIPTION "For authenticated success users, they can use internet
                 service during a certain period. Whenever this period expires,
                 users need to be re-authenticated again. This period is
                 called session time."
    ::= { webAuthMgt 5 }

webAuthQuietPeriod    OBJECT-TYPE
    SYNTAX      INTEGER (1..180)
    MAX-ACCESS  read-write
    STATUS      current
    DESCRIPTION "Specifies the re-authentication interval when the authentication
             fail attempts reach the webAuthLoginAttempts value. Unauthenticated
             user won't be authenticated during this period."
    ::= { webAuthMgt 6 }

webAuthLoginAttempts    OBJECT-TYPE
    SYNTAX      INTEGER (1..3)
    MAX-ACCESS  read-write
    STATUS      current
    DESCRIPTION "Specifies the counter that configures the authentication fail times
                 for a client. If authentication fail times reaches the specified
                 value, the client are not allowed to login for some period."
    ::= { webAuthMgt 7 }

--
-- webAuthReauthenticateMgt
--

webAuthReauthenticateMgt             OBJECT IDENTIFIER ::= { webAuthMgt 8 }

webAuthReauthenticatePort     OBJECT-TYPE
    SYNTAX      INTEGER
    MAX-ACCESS  read-write
    STATUS      current
    DESCRIPTION "Specifies the port to re-authenticate for all of its
                 authenticated hosts."
    ::= { webAuthReauthenticateMgt 1 }

webAuthReauthenticateInetAddressType     OBJECT-TYPE
    SYNTAX      InetAddressType
    MAX-ACCESS  read-write
    STATUS      current
    DESCRIPTION "Specifies host type to re-authenticate."
    ::= { webAuthReauthenticateMgt 2 }

webAuthReauthenticateInetAddress     OBJECT-TYPE
    SYNTAX      InetAddress
    MAX-ACCESS  read-write
    STATUS      current
    DESCRIPTION "Specificies host to re-authenticate."
    ::= { webAuthReauthenticateMgt 3 }

webAuthReauthenticateAction     OBJECT-TYPE
    SYNTAX      INTEGER
                {
                    noReauth     (1),
                    reauth       (2)
                }
    MAX-ACCESS  read-write
    STATUS      current
    DESCRIPTION "Action for WebAuth re-authenication. When setting this object to
                 reauth(2) to begin the re-authenticated operation, a particular
                 user is re-authenticated. When the action is finshed whether it is
                 successfully, or no action is taken, the value of this
                 object is always noReauth(1)."
    ::= { webAuthReauthenticateMgt 4 }

--
-- webAuthPortConfigTable
--

webAuthPortConfigTable   OBJECT-TYPE
    SYNTAX      SEQUENCE OF WebAuthPortConfigEntry
    MAX-ACCESS  not-accessible
    STATUS      current
    DESCRIPTION "Contains the settings for web authentication of each port."
    ::= { webAuthMgt 9 }

webAuthPortConfigEntry   OBJECT-TYPE
    SYNTAX      WebAuthPortConfigEntry
    MAX-ACCESS  not-accessible
    STATUS      current
    DESCRIPTION "A conceptual row in the webAuthPortConfigTable."
    INDEX { webAuthPortConfigPortIndex }
    ::= { webAuthPortConfigTable  1 }

WebAuthPortConfigEntry ::= SEQUENCE
{
    webAuthPortConfigPortIndex                     INTEGER,
    webAuthPortConfigStatus                        INTEGER,
    webAuthPortConfigAuthenticatedHostCount        INTEGER
}

webAuthPortConfigPortIndex      OBJECT-TYPE
    SYNTAX      INTEGER
    MAX-ACCESS  not-accessible
    STATUS      current
    DESCRIPTION "The port number of the port that may specify certain entry in the table which contains web                            authentication information."
    ::= { webAuthPortConfigEntry  1 }

webAuthPortConfigStatus     OBJECT-TYPE
    SYNTAX     EnabledStatus
    MAX-ACCESS  read-write
    STATUS      current
    DESCRIPTION "Sets enabled(1) to enable web authentication feature for each port and
                 sets disabled(2) to disable web authentication for each port."
    ::= { webAuthPortConfigEntry 2 }

webAuthPortConfigAuthenticatedHostCount      OBJECT-TYPE
    SYNTAX      INTEGER
    MAX-ACCESS  read-only
    STATUS      current
    DESCRIPTION "Displays the authenticated host counts for each port"
    ::= { webAuthPortConfigEntry 3 }

--
-- webAuthPortInfoTable
--

webAuthPortInfoTable   OBJECT-TYPE
    SYNTAX      SEQUENCE OF WebAuthPortInfoEntry
    MAX-ACCESS  not-accessible
    STATUS      current
    DESCRIPTION "Contains the information for web authentication of each port."
    ::= { webAuthMgt 10 }

webAuthPortInfoEntry   OBJECT-TYPE
    SYNTAX      WebAuthPortInfoEntry
    MAX-ACCESS  not-accessible
    STATUS      current
    DESCRIPTION "A conceptual row in the webAuthPortTable."
    INDEX { webAuthPortInfoPortIndex, webAuthPortInfoPortAuthSuccessIndex}
    ::= { webAuthPortInfoTable 1 }

WebAuthPortInfoEntry ::= SEQUENCE
{
    webAuthPortInfoPortIndex                  INTEGER,
    webAuthPortInfoPortAuthSuccessIndex       INTEGER,
    webAuthPortInfoInetAddressType            InetAddressType,
    webAuthPortInfoInetAddress                InetAddress,
    webAuthPortInfoRemainingSessiontime       INTEGER,
    webAuthPortInfoStatus                     INTEGER
}

webAuthPortInfoPortIndex      OBJECT-TYPE
    SYNTAX      INTEGER
    MAX-ACCESS  not-accessible
    STATUS      current
    DESCRIPTION "The port number for which this entry contains web authentication information."
    ::= { webAuthPortInfoEntry  1 }

webAuthPortInfoPortAuthSuccessIndex      OBJECT-TYPE
    SYNTAX      INTEGER
    MAX-ACCESS  not-accessible
    STATUS      current
    DESCRIPTION "The authentication success number of port for which this entry contains web authentication information."
    ::= { webAuthPortInfoEntry  2 }

webAuthPortInfoInetAddressType      OBJECT-TYPE
    SYNTAX      InetAddressType
    MAX-ACCESS  read-only
    STATUS      current
    DESCRIPTION "This object indicates the type of IP address denoted in webAuthPortInfoIpAddress type."
    ::= { webAuthPortInfoEntry  3 }

webAuthPortInfoInetAddress      OBJECT-TYPE
    SYNTAX      InetAddress
    MAX-ACCESS  read-only
    STATUS      current
    DESCRIPTION "The IP address which may specify the entry containing web authentication information."
    ::= { webAuthPortInfoEntry  4 }

webAuthPortInfoRemainingSessiontime      OBJECT-TYPE
    SYNTAX      INTEGER
    MAX-ACCESS  read-only
    STATUS      current
   DESCRIPTION "The remaining session time for authenticated hosts. During this
                period, they may use internet resource. When the session time expires, they
                will need to re-authenticate again."

    ::= { webAuthPortInfoEntry 5 }

webAuthPortInfoStatus    OBJECT-TYPE
    SYNTAX      INTEGER
                {
                    authenticated      (1)
                }
    MAX-ACCESS  read-only
    STATUS      current
    DESCRIPTION "Displays the web authentication status for each port.
                 authenticated (1) means the user is authenticated."
    ::= { webAuthPortInfoEntry 6 }

--
-- layer3Mgt
--

-- Management for layer 3 settings and protocols.

arpMgt              OBJECT IDENTIFIER ::= { layer3Mgt 1 }
ripMgt              OBJECT IDENTIFIER ::= { layer3Mgt 2 }
ospfMgt             OBJECT IDENTIFIER ::= { layer3Mgt 3 }
dvmrpMgt            OBJECT IDENTIFIER ::= { layer3Mgt 4 }
routeMgt            OBJECT IDENTIFIER ::= { layer3Mgt 5 }

-- arpMgt

arpCacheDeleteAll OBJECT-TYPE
        SYNTAX      INTEGER
                    {
                        delete(1),
                        noDelete(2)
                    }
        MAX-ACCESS  read-write
        STATUS      current
        DESCRIPTION "To delete all dynamic entries in the ARP cache,
                     write this variable to delete(1). Writing this variable
                     to noDelete(2) has no effect on the device. When
                     read, this variable always returns noDelete(2)."
        ::= { arpMgt 1 }

arpCacheTimeout OBJECT-TYPE
        SYNTAX      Integer32(300..86400)
        MAX-ACCESS  read-write
        STATUS      current
        DESCRIPTION "Timeout is provided for entries in the
                     ARP Cache. It is for dynamic mapping only.
                     Static mapping by creating an entry
                     that associates a logical address with a physical
                     address is never aged out."
        ::= { arpMgt 2 }

arpTrafficStatistics OBJECT IDENTIFIER ::= { arpMgt 3 }

arpStatSendRequestPackets OBJECT-TYPE
        SYNTAX      Counter32
        MAX-ACCESS  read-only
        STATUS      current
        DESCRIPTION "The number of ARP Request packets sent by
                     the ARP process."
        ::= { arpTrafficStatistics 1 }

arpStatRcvRequestPackets OBJECT-TYPE
        SYNTAX      Counter32
        MAX-ACCESS  read-only
        STATUS      current
        DESCRIPTION "The number of ARP Request packets received by
                     the ARP process."
        ::= { arpTrafficStatistics 2 }

arpStatSendReplyPackets OBJECT-TYPE
        SYNTAX      Counter32
        MAX-ACCESS  read-only
        STATUS      current
        DESCRIPTION "The number of ARP Reply packets sent by
                     the ARP process."
        ::= { arpTrafficStatistics 3 }

arpStatRcvReplyPackets OBJECT-TYPE
        SYNTAX      Counter32
        MAX-ACCESS  read-only
        STATUS      current
        DESCRIPTION "The number of ARP Reply packets received by
                     the ARP process."
        ::= { arpTrafficStatistics 4 }


arpProxyArpTable OBJECT-TYPE
        SYNTAX      SEQUENCE OF ArpProxyArpEntry
        MAX-ACCESS  not-accessible
        STATUS      current
        DESCRIPTION "A list of Proxy ARP status. This table has entries
                     for all static VLANs."
        ::= { arpMgt 4 }

arpProxyArpEntry OBJECT-TYPE
        SYNTAX      ArpProxyArpEntry
        MAX-ACCESS  not-accessible
        STATUS      current
        DESCRIPTION "An entry in the table, containing information
                     about Proxy ARP configuration."
        INDEX       { arpProxyArpIfIndex }
        ::= { arpProxyArpTable 1 }

ArpProxyArpEntry ::= SEQUENCE
{
    arpProxyArpIfIndex          Integer32,
    arpProxyArpStatus           EnabledStatus
}

arpProxyArpIfIndex OBJECT-TYPE
        SYNTAX      Integer32
        MAX-ACCESS  not-accessible
        STATUS      current
        DESCRIPTION "This is defined as a VLAN interface.
                     A routing interface is a VLAN that binds an IP
                     subnet."
        ::= { arpProxyArpEntry 1 }

arpProxyArpStatus OBJECT-TYPE
        SYNTAX      EnabledStatus
        MAX-ACCESS  read-write
        STATUS      current
        DESCRIPTION "Enable or disable proxy ARP process on an interface."
        DEFVAL      { enabled }
        ::= { arpProxyArpEntry 2 }

arpCacheTimeoutInMinutes OBJECT-TYPE
        SYNTAX      Integer32(0..1440)
        MAX-ACCESS  read-write
        STATUS      current
        DESCRIPTION "Timeout is provided for entries in the
                     ARP Cache. It is for dynamic mapping only.
                     Static mapping by creating an entry
                     that associates a logical address with a physical
                     address is never aged out.
                     Setting this to 0 means that timeout is disabled."
        ::= { arpMgt 5 }

-- ripMgt


ripTimers OBJECT IDENTIFIER ::= { ripMgt 1 }

ripUpdateTime OBJECT-TYPE
        SYNTAX      Integer32 (15..60)
        MAX-ACCESS  read-write
        STATUS      current
        DESCRIPTION "The update time in seconds controls the advertising of regular
                     update messages. In the real implemention, the actual timer is
                     this value offset by a small random time (+/- 0 to 5 seconds)
                     each time it is set."
        DEFVAL      { 30 }
        ::= { ripTimers 1 }

ripTimeoutTime OBJECT-TYPE
        SYNTAX      Integer32 (90..360)
        MAX-ACCESS  read-only
        STATUS      current
        DESCRIPTION "The timeout timer in seconds governs the validity of a route.
                     It is initialized when a route is established, and any time
                     an update message is received for the route. If the setting time
                     elapses from the last time the timeout was initialized, the route
                     is considered to have expired, and the hop count of the route is
                     set to infinite. It should be at least three times the value of
                     the update timer."
        DEFVAL      { 180 }
        ::= { ripTimers 2 }

ripGarbageCollectionTime OBJECT-TYPE
        SYNTAX      Integer32 (60..240)
        MAX-ACCESS  read-only
        STATUS      current
        DESCRIPTION "When the information about a route becomes invalid, the system
                     does not immediately purge that route from its table. Instead,
                     it continues to advertise the route with an infinite metric
                     At the same time, the garbage-collection timer is set for that
                     route. When the count reaches zero, the route is purged from the
                     the table. This timer allows neighbors to become aware of
                     the invalidity of a route prior to purging."
        DEFVAL      { 120 }
        ::= { ripTimers 3 }

ripRoutingProcessStatus OBJECT-TYPE
        SYNTAX      EnabledStatus
        MAX-ACCESS  read-write
        STATUS      current
        DESCRIPTION "Enable or disable RIP routing process on a system."
        DEFVAL      { disabled }
        ::= { ripMgt 2 }

ripRouterVersion OBJECT-TYPE
        SYNTAX      INTEGER
                    {
                        byInterface(1),
                        rip1(2),
                        rip2(3)
                    }
        MAX-ACCESS  read-write
        STATUS      current
        DESCRIPTION "To specify an RIP version used globally by the router."
        DEFVAL      { rip2 }
        ::= { ripMgt 3 }



ripInstabilityPreventingTable OBJECT-TYPE
        SYNTAX      SEQUENCE OF RipInstabilityPreventingEntry
        MAX-ACCESS  not-accessible
        STATUS      current
        DESCRIPTION "A list of RIP instability preventing status."
        ::= { ripMgt 4 }

ripInstabilityPreventingEntry OBJECT-TYPE
        SYNTAX      RipInstabilityPreventingEntry
        MAX-ACCESS  not-accessible
        STATUS      current
        DESCRIPTION "An entry in the table, containing information
                     about RIP instability preventing configuration.
                     The ifIndex index is a VLAN's ifIndex."
        INDEX       { ripVlanIndex }
        ::= { ripInstabilityPreventingTable 1 }

RipInstabilityPreventingEntry ::= SEQUENCE
{
    ripVlanIndex             Integer32,
    ripSplitHorizonStatus   INTEGER
}


ripVlanIndex OBJECT-TYPE
        SYNTAX      Integer32
        MAX-ACCESS  not-accessible
        STATUS      current
        DESCRIPTION "This is defined as a VLAN interface.
                     A routing interface is a VLAN and an IP subnet bound to it."
        ::= { ripInstabilityPreventingEntry 1 }

ripSplitHorizonStatus OBJECT-TYPE
        SYNTAX      INTEGER
                    {
                        splitHorizon(1),
                        poisonReverse(2),
                        none(3)
                    }
        MAX-ACCESS  read-write
        STATUS      current
        DESCRIPTION "Enable or disable RIP poison reverse on an interface."
        ::= { ripInstabilityPreventingEntry 2 }


ripStatisticsReset OBJECT-TYPE
        SYNTAX      INTEGER
                    {
                        reset(1),
                        noReset(2)
                    }
        MAX-ACCESS  read-write
        STATUS      current
        DESCRIPTION "Write it to reset(1), the following objects in RFC 1724
                     should be reset:
                     1. Global Counters:
                        'rip2GlobalRouteChanges',
                        'rip2GlobalQueries'.
                     2. Interface Status Table, for each 'rip2IfStatAddress':
                        'rip2IfStatRcvBadPackets',
                        'rip2IfStatRcvBadRoutes',
                        'rip2IfStatSendUpdates'
                     3. Peer Table, for each 'rip2PeerAddress' and 'rip2PeerDomain',
                        'rip2PeerRcvBadPackets',
                        'rip2PeerRcvBadRoutes'
                     When read this value always is noReset(2)."
        ::= { ripMgt 5 }

ripNetworkAddrTable OBJECT-TYPE
        SYNTAX      SEQUENCE OF RipNetworkAddrEntry
        MAX-ACCESS  not-accessible
        STATUS      current
        DESCRIPTION "The RIF network address table."
        ::= { ripMgt 6 }

ripNetworkAddrEntry OBJECT-TYPE
        SYNTAX      RipNetworkAddrEntry
        MAX-ACCESS  not-accessible
        STATUS      current
        DESCRIPTION "A conceptual row of the ripNetworkAddrTable."
        INDEX       { ripNetworkAddrAddress }
        ::= { ripNetworkAddrTable 1 }

RipNetworkAddrEntry ::= SEQUENCE
{
    ripNetworkAddrAddress  IpAddress,
    ripNetworkAddrStatus   ValidStatus
}


ripNetworkAddrAddress OBJECT-TYPE
        SYNTAX      IpAddress
        MAX-ACCESS  not-accessible
        STATUS      current
        DESCRIPTION "The RIP Network address."
        ::= { ripNetworkAddrEntry 1 }

ripNetworkAddrStatus OBJECT-TYPE
        SYNTAX      ValidStatus
        MAX-ACCESS  read-create
        STATUS      current
        DESCRIPTION "Set this variable to create or destroy an RIP network address."
        ::= { ripNetworkAddrEntry 2 }

-- ospfMgt

ospfSystemGroup OBJECT IDENTIFIER ::= { ospfMgt 1 }

ospfRouterIdType OBJECT-TYPE
        SYNTAX      INTEGER
                    {
                        auto(1),
                        manual(2)
                    }
        MAX-ACCESS  read-only
        STATUS      current
        DESCRIPTION "Set router ID automatically or manually."
        DEFVAL { auto }
        ::= { ospfSystemGroup 1 }

ospfRfc1583CompatibleState OBJECT-TYPE
        SYNTAX      EnabledStatus
        MAX-ACCESS  read-write
        STATUS      current
        DESCRIPTION     "Enable or disable rfc1583 compatibility."
        DEFVAL { disabled }
        ::= { ospfSystemGroup 2 }

ospfAutoCost OBJECT-TYPE
        SYNTAX   Integer32
        MAX-ACCESS  read-write
        STATUS      current
        DESCRIPTION "Set the reference bandwith of auto cost, the unit is Mbps."
        DEFVAL { 100 }
        ::= { ospfSystemGroup 3 }

ospfOriginateDefaultRoute OBJECT-TYPE
        SYNTAX   EnabledStatus
        MAX-ACCESS  read-write
        STATUS      current
        DESCRIPTION     "Enable or disable ASBR to generate a default external
                        route into an OSPF domain if the default route already
                        exists."
        DEFVAL { disabled }
        ::= { ospfSystemGroup 4 }

ospfAdvertiseDefaultRoute OBJECT-TYPE
        SYNTAX   INTEGER
            {
                   always(1),
                   notAlways(2)
                }
        MAX-ACCESS  read-write
        STATUS      current
        DESCRIPTION     "If enabled, always advertises the default route regardless
                        of whether the default route exists."
        DEFVAL { notAlways }
        ::= { ospfSystemGroup 5 }

ospfExternalMetricType OBJECT-TYPE
        SYNTAX   INTEGER
            {
                   type1 (1),
                    type2 (2)
                }
        MAX-ACCESS  read-write
        STATUS      current
        DESCRIPTION "External link type associated with the default route
                     advertised into the OSPF routing domain."
        DEFVAL { type2 }
        ::= { ospfSystemGroup 6 }

ospfDefaultExternalMetric OBJECT-TYPE
        SYNTAX      OspfBigMetric
        MAX-ACCESS  read-write
        STATUS      current
        DESCRIPTION "Metric used for generating the default route."
        DEFVAL { 10 }
        ::= { ospfSystemGroup 7 }

ospfSpfHoldTime OBJECT-TYPE
        SYNTAX   Integer32 (0..65535)
        MAX-ACCESS  read-write
        STATUS      current
        DESCRIPTION     "Sets the hold time between two consecutive SPF calculations."
        DEFVAL { 10 }
        ::= { ospfSystemGroup 8 }

ospfSpfDelayTime OBJECT-TYPE
        SYNTAX   Integer32 (0..65535)
        MAX-ACCESS  read-write
        STATUS      current
        DESCRIPTION "Sets the delay time to calculate SPF Delay time, in seconds, between
                         when OSPF receives a topology change and when it starts an SPF calculation."
        DEFVAL { 5 }
        ::= { ospfSystemGroup 9 }

ospfAreaNumber OBJECT-TYPE
        SYNTAX   Integer32
        MAX-ACCESS  read-only
        STATUS      current
        DESCRIPTION "Records the OSPF area numbers."

        DEFVAL { 0 }
        ::= { ospfSystemGroup 10 }

ospfNssaTable OBJECT-TYPE
        SYNTAX   SEQUENCE OF OspfNssaEntry
        MAX-ACCESS   not-accessible
        STATUS   current
        DESCRIPTION
           "A conceptually table for ospfNssaEntry."
        ::= {ospfMgt 2 }

ospfNssaEntry OBJECT-TYPE
        SYNTAX   OspfNssaEntry
        MAX-ACCESS   not-accessible
        STATUS   current
        DESCRIPTION
           "A conceptually row for ospfNssaTable."
        INDEX { ospfNssaAreaId }
      ::= { ospfNssaTable 1 }

OspfNssaEntry ::= SEQUENCE
      {
        ospfNssaAreaId                     OspfAreaID,
        ospfNssaRedistributeStatus         EnabledStatus,
        ospfNssaOriginateDefaultInfoStatus EnabledStatus,
        ospfNssaStatus                     RowStatus
      }

ospfNssaAreaId OBJECT-TYPE
        SYNTAX       OspfAreaID
        MAX-ACCESS   not-accessible
        STATUS       current
        DESCRIPTION "The 32-bit identifier for the NSSA. On creation,
            this can be derived from the instance."
       ::= { ospfNssaEntry 1 }

ospfNssaRedistributeStatus OBJECT-TYPE
        SYNTAX       EnabledStatus
        MAX-ACCESS   read-create
        STATUS       current
        DESCRIPTION
           "Enabled or disabled to import routes only into the normal areas,
            but not into the NSSA area."
        DEFVAL { enabled }
       ::= { ospfNssaEntry 2 }

ospfNssaOriginateDefaultInfoStatus OBJECT-TYPE
        SYNTAX       EnabledStatus
        MAX-ACCESS   read-create
        STATUS       current
        DESCRIPTION "Enable or disable to generate a Type 7 default into the NSSA area."

         DEFVAL { disabled }
       ::= { ospfNssaEntry 3 }

ospfNssaStatus OBJECT-TYPE
        SYNTAX       RowStatus
        MAX-ACCESS   read-create
        STATUS       current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
       ::= { ospfNssaEntry 4 }

ospfRedistributeTable OBJECT-TYPE
        SYNTAX   SEQUENCE OF OspfRedistributeEntry
        MAX-ACCESS   not-accessible
        STATUS   current
        DESCRIPTION
           "The conceptual table of all of ospfRedistributeEntry."
        ::= {ospfMgt 3 }


ospfRedistributeEntry OBJECT-TYPE
        SYNTAX       OspfRedistributeEntry
        MAX-ACCESS   not-accessible
        STATUS       current
        DESCRIPTION
           "The conceptual row for ospfRedistributeTable."
      INDEX { ospfRedistributeProtocol }
      ::= { ospfRedistributeTable 1 }

OspfRedistributeEntry ::= SEQUENCE
{
         ospfRedistributeProtocol   INTEGER,
         ospfRedistributeMetricType INTEGER,
         ospfRedistributeMetric     OspfBigMetric,
         ospfRedistributeStatus     RowStatus
}

ospfRedistributeProtocol OBJECT-TYPE
        SYNTAX      INTEGER
                {
                  rip(1),
                  static(2)
                }
        MAX-ACCESS   not-accessible
        STATUS       current
        DESCRIPTION "Protocol ID. Static is not supported now."

       ::= { ospfRedistributeEntry 1 }

ospfRedistributeMetricType OBJECT-TYPE
        SYNTAX      INTEGER
                {
                      type1(1),
                      type2(2)
                    }
        MAX-ACCESS   read-create
        STATUS       current
        DESCRIPTION
           "Metric type."
        DEFVAL {type2}
       ::= { ospfRedistributeEntry 2 }

ospfRedistributeMetric OBJECT-TYPE
        SYNTAX       OspfBigMetric
        MAX-ACCESS   read-create
        STATUS       current
        DESCRIPTION
           "Metric value."
        DEFVAL {10}
       ::= { ospfRedistributeEntry 3 }

ospfRedistributeStatus OBJECT-TYPE
        SYNTAX       RowStatus
        MAX-ACCESS   read-create
        STATUS       current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
       ::= { ospfRedistributeEntry 4 }

ospfSummaryAddressTable OBJECT-TYPE
        SYNTAX   SEQUENCE OF OspfSummaryAddressEntry
        MAX-ACCESS   not-accessible
        STATUS   current
        DESCRIPTION
           "The conceptual table of all of ospfSummaryAddressEntry."
      ::= {ospfMgt 4}

ospfSummaryAddressEntry OBJECT-TYPE
       SYNTAX       OspfSummaryAddressEntry
       MAX-ACCESS   not-accessible
       STATUS       current
       DESCRIPTION
           "The conceptual row for ospfSummaryAddressTable."
       INDEX { ospfSummaryAddress,ospfSummaryMask }
       ::= { ospfSummaryAddressTable 1 }

OspfSummaryAddressEntry ::= SEQUENCE
{
       ospfSummaryAddress   IpAddress,
       ospfSummaryMask      IpAddress,
       ospfSummaryStatus    RowStatus
}

ospfSummaryAddress OBJECT-TYPE
        SYNTAX       IpAddress
        MAX-ACCESS   not-accessible
        STATUS       current
        DESCRIPTION
           "Summary address."
        ::= { ospfSummaryAddressEntry 1 }

ospfSummaryMask OBJECT-TYPE
        SYNTAX       IpAddress
        MAX-ACCESS   not-accessible
        STATUS       current
        DESCRIPTION
           "Summary mask."
       ::= { ospfSummaryAddressEntry 2 }


ospfSummaryStatus OBJECT-TYPE
        SYNTAX       RowStatus
        MAX-ACCESS   read-create
        STATUS       current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
       ::= { ospfSummaryAddressEntry 3 }

ospfNetworkAreaAddressTable OBJECT-TYPE
        SYNTAX   SEQUENCE OF OspfNetworkAreaAddressEntry
        MAX-ACCESS   not-accessible
        STATUS   current
        DESCRIPTION
           "The conceptual table of all of ospfNetworkAreaAddressEntry."
        ::= {ospfMgt 5 }

ospfNetworkAreaAddressEntry OBJECT-TYPE
        SYNTAX       OspfNetworkAreaAddressEntry
        MAX-ACCESS   not-accessible
        STATUS       current
        DESCRIPTION
           "The conceptual row for ospfNetworkAreaAddressTable."
        INDEX { ospfNetworkAareaAddress,ospfNetworkAreaMask }
        ::= { ospfNetworkAreaAddressTable 1 }

OspfNetworkAreaAddressEntry ::= SEQUENCE
{
       ospfNetworkAareaAddress  IpAddress,
       ospfNetworkAreaMask      IpAddress,
       ospfNetworkAreaAreaId    IpAddress,
       ospfNetworkAreaStatus    RowStatus
}

ospfNetworkAareaAddress OBJECT-TYPE
        SYNTAX       IpAddress
        MAX-ACCESS   not-accessible
        STATUS       current
        DESCRIPTION
           "NetworkArea address."
       ::= { ospfNetworkAreaAddressEntry 1 }

ospfNetworkAreaMask OBJECT-TYPE
        SYNTAX   IpAddress
        MAX-ACCESS   not-accessible
        STATUS   current
        DESCRIPTION
           "NetworkArea mask."
       ::= { ospfNetworkAreaAddressEntry 2 }

ospfNetworkAreaAreaId OBJECT-TYPE
        SYNTAX       IpAddress
        MAX-ACCESS   read-create
        STATUS       current
        DESCRIPTION
           "NetworkArea area ID."
       ::= { ospfNetworkAreaAddressEntry 3 }

ospfNetworkAreaStatus OBJECT-TYPE
        SYNTAX       RowStatus
        MAX-ACCESS   read-create
        STATUS       current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
       ::= { ospfNetworkAreaAddressEntry 4 }

ospfPassiveInterfaceDefault OBJECT-TYPE
    SYNTAX     EnabledStatus
    MAX-ACCESS read-write
    STATUS     current
    DESCRIPTION
         "The parameter to enable or disable the OSPF passive interface feature
          on this device. Setting this to enabled(1) sets all interfaces as passive.
          It indicates to disable the all interfaces from sending and receiving
          OSPF packets to avoid undesired route updating. Setting this to disabled(2)
          sets all interfaces as active."
    ::= { ospfMgt 6 }

ospfPassiveInterfaceVlanTable OBJECT-TYPE
        SYNTAX      SEQUENCE OF OspfPassiveInterfaceVlanEntry
        MAX-ACCESS  not-accessible
        STATUS      current
        DESCRIPTION "Table for configuring OSPF passive interface of each VLAN."
        ::= { ospfMgt 7 }

ospfPassiveInterfaceVlanEntry OBJECT-TYPE
        SYNTAX      OspfPassiveInterfaceVlanEntry
        MAX-ACCESS  not-accessible
        STATUS      current
        DESCRIPTION "Entry for configuring OSPF passive interface of each VLAN."
        INDEX       { ospfPassiveInterfaceVlanIndex }
        ::= { ospfPassiveInterfaceVlanTable 1 }

OspfPassiveInterfaceVlanEntry ::= SEQUENCE
{
    ospfPassiveInterfaceVlanIndex     Unsigned32,
    ospfPassiveInterfaceVlanEnable    EnabledStatus
}

ospfPassiveInterfaceVlanIndex OBJECT-TYPE
        SYNTAX      Unsigned32
        MAX-ACCESS  not-accessible
        STATUS      current
        DESCRIPTION "The interface identified by a particular value of
                     this index is the same interface identified by the
                     same value of dot1qVlanIndex in the Q-BRIDGE-MIB."
        ::= { ospfPassiveInterfaceVlanEntry 1 }

ospfPassiveInterfaceVlanEnable OBJECT-TYPE
        SYNTAX      EnabledStatus
        MAX-ACCESS  read-write
        STATUS      current
        DESCRIPTION "Parameter to enable or disable OSPF passive interface of this VLAN."
        ::= { ospfPassiveInterfaceVlanEntry 2 }

--
-- dvmrpMgt
--
dvmrpScalar     OBJECT IDENTIFIER ::= { dvmrpMgt 1 }

dvmrpVersionString OBJECT-TYPE
    SYNTAX     DisplayString
    MAX-ACCESS read-only
    STATUS     current
    DESCRIPTION
            "The router's DVMRP version information. Similar to
            sysDescr in MIB-II, this is a free-form field which can be
            used to display vendor-specific information."
    ::= { dvmrpScalar 1 }

-- dvmrpScalar 2 was previously used for a global
-- Generation ID.  However, the DVMRP spec changed it to
-- a per-interface parameter.
dvmrpNumRoutes OBJECT-TYPE
    SYNTAX     Gauge32
    MAX-ACCESS read-only
    STATUS     current
    DESCRIPTION
            "The number of entries in the routing table. This can be
            used to monitor the routing table size."
    ::= { dvmrpScalar 3 }

dvmrpReachableRoutes OBJECT-TYPE
    SYNTAX     Gauge32
    MAX-ACCESS read-only
    STATUS     current
    DESCRIPTION
            "The number of entries in the routing table with non-infinite
            metrics. This can be used to detect network partitions
            by observing the ratio of reachable routes to total routes."
    ::= { dvmrpScalar 4 }

-- The DVMRP Interface Table

dvmrpInterfaceTable OBJECT-TYPE
    SYNTAX     SEQUENCE OF DvmrpInterfaceEntry
    MAX-ACCESS not-accessible
    STATUS     current
    DESCRIPTION
            "The (conceptual) table listing the router's multicast-capable
             interfaces."
    ::= { dvmrpMgt 2 }

dvmrpInterfaceEntry OBJECT-TYPE
    SYNTAX     DvmrpInterfaceEntry
    MAX-ACCESS not-accessible
    STATUS     current
    DESCRIPTION
            "An entry (conceptual row) in the dvmrpInterfaceTable. This
            row augments ipMRouteInterfaceEntry in the IP multicast MIB,
            where the threshold object resides."
    INDEX      { dvmrpInterfaceIndex }
    ::= { dvmrpInterfaceTable 1 }

DvmrpInterfaceEntry ::= SEQUENCE {
    dvmrpInterfaceIndex                 InterfaceIndex,
    dvmrpInterfaceLocalAddress          IpAddress,
    dvmrpInterfaceMetric                Integer32,
    dvmrpInterfaceStatus                RowStatus,
    dvmrpInterfaceRcvBadPkts            Counter32,
    dvmrpInterfaceRcvBadRoutes          Counter32,
    dvmrpInterfaceSentRoutes            Counter32,
    dvmrpInterfaceKey                   SnmpAdminString,
    dvmrpInterfaceKeyVersion            Integer32,
    dvmrpInterfaceGenerationId          Integer32
}

dvmrpInterfaceIndex OBJECT-TYPE
    SYNTAX     InterfaceIndex
    MAX-ACCESS not-accessible
    STATUS     current
    DESCRIPTION
            "The ifIndex value of the interface for which DVMRP is
            enabled."
    ::= { dvmrpInterfaceEntry 1 }

dvmrpInterfaceLocalAddress OBJECT-TYPE
    SYNTAX     IpAddress
    MAX-ACCESS read-create
    STATUS     current
    DESCRIPTION
            "The IP address this system will use as a source address on
            this interface. On unnumbered interfaces, it must be the
            same value as dvmrpInterfaceLocalAddress for some interface
            on the system."
    ::= { dvmrpInterfaceEntry 2 }

dvmrpInterfaceMetric OBJECT-TYPE
    SYNTAX     Integer32 (1..31)
    MAX-ACCESS read-create
    STATUS     current
    DESCRIPTION
            "The distance metric for this interface which is used to
            calculate distance vectors."
    DEFVAL     { 1 }
    ::= { dvmrpInterfaceEntry 3 }

dvmrpInterfaceStatus OBJECT-TYPE
    SYNTAX     RowStatus
    MAX-ACCESS read-create
    STATUS     current
        DESCRIPTION
            "The status of this conceptual row entry. This object isused to manage the
            creation and deletion of conceptual rows.

            The status column has six defined values:

                 - 'active', which indicates that the conceptual row is
                 available for use by the managed device;

                 - 'notInService', which indicates that the conceptual
                 row exists in the agent, but is unavailable for use by
                 the managed device (see NOTE below);

                 - 'notReady', which indicates that the conceptual row
                 exists in the agent, but is missing information
                 necessary in order to be available for use by the
                 managed device;

                 - 'createAndGo', which is supplied by a management
                 station wishing to create a new instance of a
                 conceptual row and to have its status automatically set
                 to active, making it available for use by the managed
                 device;

                 - 'createAndWait', which is supplied by a management
                 station wishing to create a new instance of a
                 conceptual row (but not make it available for use by
                 the managed device); and,

                 - 'destroy', which is supplied by a management station
                 wishing to delete all of the instances associated with
                 an existing conceptual row.

            Whereas five of the six values (all except 'notReady') may
            be specified in a management protocol set operation, only
            three values will be returned in response to a management
            protocol retrieval operation:  'notReady', 'notInService' or
            'active'.  That is, when queried, an existing conceptual row
            has only three states:  it is either available for use by
            the managed device (the status column has value 'active');
            it is not available for use by the managed device, though
            the agent has sufficient information to make it so (the
            status column has value 'notInService'); or, it is not
            available for use by the managed device, and an attempt to
            make it so would fail because the agent has insufficient
            information (the state column has value 'notReady').

            For a detailed description of this object, please refer to
            SNMPv2-TC MIB."
    ::= { dvmrpInterfaceEntry 4 }

dvmrpInterfaceRcvBadPkts OBJECT-TYPE
    SYNTAX     Counter32
    MAX-ACCESS read-only
    STATUS     current
    DESCRIPTION
            "The number of DVMRP messages received on the interface by
            the DVMRP process which were subsequently discarded as
            invalid (e.g. invalid packet format, or a route report from
            an unknown neighbor)."
    ::= { dvmrpInterfaceEntry 5 }

dvmrpInterfaceRcvBadRoutes OBJECT-TYPE
    SYNTAX     Counter32
    MAX-ACCESS read-only
    STATUS     current
    DESCRIPTION
            "The number of routes, in valid DVMRP packets, which were
            ignored because the entry was invalid."
    ::= { dvmrpInterfaceEntry 6 }

dvmrpInterfaceSentRoutes OBJECT-TYPE
    SYNTAX     Counter32
    MAX-ACCESS read-only
    STATUS     current
    DESCRIPTION
            "The number of routes, in DVMRP Report packets, which have
            been sent on this interface. Together with
            dvmrpNeighborRcvRoutes as a peer, this object is useful for
            detecting routes being lost."
    ::= { dvmrpInterfaceEntry 7 }

dvmrpInterfaceKey OBJECT-TYPE
    SYNTAX     SnmpAdminString
    MAX-ACCESS read-create
    STATUS     current
    DESCRIPTION
            "The (shared) key for authenticating neighbors on this
            interface. This object is intended solely for the purpose
            of setting the interface key, and must be accessible only
            via requests using both authentication and privacy. The
            agent may report an empty string in response to get, get-next,
            and get-bulk requests."
    ::= { dvmrpInterfaceEntry 8 }

dvmrpInterfaceKeyVersion OBJECT-TYPE
    SYNTAX     Integer32
    MAX-ACCESS read-create
    STATUS     current
    DESCRIPTION
            "The highest version number of all known interface keys for
            this interface used for authenticating neighbors."
    ::= { dvmrpInterfaceEntry 9 }

dvmrpInterfaceGenerationId OBJECT-TYPE
    SYNTAX     Integer32
    MAX-ACCESS read-only
    STATUS     current
    DESCRIPTION
            "The generation identifier for the interface. This is used
            by neighboring routers to detect whether the DVMRP routing
            table should be resent."
    ::= { dvmrpInterfaceEntry 10 }

-- The DVMRP Neighbor Table

dvmrpNeighborTable OBJECT-TYPE
    SYNTAX     SEQUENCE OF DvmrpNeighborEntry
    MAX-ACCESS not-accessible
    STATUS     current
    DESCRIPTION
            "The (conceptual) table listing the router's DVMRP
            neighbors, as discovered by receiving DVMRP messages."
    ::= { dvmrpMgt 3 }

dvmrpNeighborEntry OBJECT-TYPE
    SYNTAX     DvmrpNeighborEntry
    MAX-ACCESS not-accessible
    STATUS     current
    DESCRIPTION
            "An entry (conceptual row) in the dvmrpNeighborTable."
    INDEX      { dvmrpNeighborIfIndex, dvmrpNeighborAddress }
    ::= { dvmrpNeighborTable 1 }

DvmrpNeighborEntry ::= SEQUENCE {
    dvmrpNeighborIfIndex         InterfaceIndex,
    dvmrpNeighborAddress         IpAddress,
    dvmrpNeighborUpTime          TimeTicks,
    dvmrpNeighborExpiryTime      TimeTicks,
    dvmrpNeighborGenerationId    Integer32,
    dvmrpNeighborMajorVersion    Integer32,
    dvmrpNeighborMinorVersion    Integer32,
    dvmrpNeighborCapabilities    BITS,
    dvmrpNeighborRcvRoutes       Counter32,
    dvmrpNeighborRcvBadPkts      Counter32,
    dvmrpNeighborRcvBadRoutes    Counter32,
    dvmrpNeighborState           INTEGER
}

dvmrpNeighborIfIndex OBJECT-TYPE
    SYNTAX     InterfaceIndex
    MAX-ACCESS not-accessible
    STATUS     current
    DESCRIPTION
            "The value of ifIndex for the virtual interface used to
            reach this DVMRP neighbor."
    ::= { dvmrpNeighborEntry 1 }

dvmrpNeighborAddress OBJECT-TYPE
    SYNTAX     IpAddress
    MAX-ACCESS not-accessible
    STATUS     current
    DESCRIPTION
            "The IP address of the DVMRP neighbor for which this entry
            contains information."
    ::= { dvmrpNeighborEntry 2 }

dvmrpNeighborUpTime OBJECT-TYPE
    SYNTAX     TimeTicks
    MAX-ACCESS read-only
    STATUS     current
    DESCRIPTION
            "The time since this DVMRP neighbor (last) became a neighbor
            of the local router."
    ::= { dvmrpNeighborEntry 3 }

dvmrpNeighborExpiryTime OBJECT-TYPE
    SYNTAX     TimeTicks
    MAX-ACCESS read-only
    STATUS     current
    DESCRIPTION
            "The minimum time remaining before this DVMRP neighbor will
            be aged out."
    ::= { dvmrpNeighborEntry 4 }

dvmrpNeighborGenerationId OBJECT-TYPE
    SYNTAX     Integer32
    MAX-ACCESS read-only
    STATUS     current
    DESCRIPTION
            "The neighboring router's generation identifier."
    ::= { dvmrpNeighborEntry 5 }

dvmrpNeighborMajorVersion OBJECT-TYPE
    SYNTAX     Integer32 (0..255)
    MAX-ACCESS read-only
    STATUS     current
    DESCRIPTION
            "The neighboring router's major DVMRP version number."
    ::= { dvmrpNeighborEntry 6 }

dvmrpNeighborMinorVersion OBJECT-TYPE
    SYNTAX     Integer32 (0..255)
    MAX-ACCESS read-only
    STATUS     current
    DESCRIPTION
            "The neighboring router's minor DVMRP version number."
    ::= { dvmrpNeighborEntry 7 }

dvmrpNeighborCapabilities OBJECT-TYPE
    SYNTAX     BITS {
                   leaf(0),
                   prune(1),
                   generationID(2),
                   mtrace(3)
               }
    MAX-ACCESS read-only
    STATUS     current
    DESCRIPTION
            "This object describes the neighboring router's
            capabilities. The leaf bit indicates that the neighbor has
            only one interface with neighbors. The prune bit indicates
            that the neighbor supports pruning. The generationID bit
            indicates that the neighbor sends its generationID in Probe
            messages. The mtrace bit indicates that the neighbor can
            handle mtrace requests."
    ::= { dvmrpNeighborEntry 8 }

dvmrpNeighborRcvRoutes OBJECT-TYPE
    SYNTAX     Counter32
    MAX-ACCESS read-only
    STATUS     current
    DESCRIPTION
            "The total number of routes received in valid DVMRP packets
            from this neighbor.This can be used to diagnose problems
            such as unicast route injection, as well as giving
            an indication of the level of DVMRP route exchange
            activity."
    ::= { dvmrpNeighborEntry 9 }

dvmrpNeighborRcvBadPkts OBJECT-TYPE
    SYNTAX     Counter32
    MAX-ACCESS read-only
    STATUS     current
    DESCRIPTION
            "The number of packet received from this neighbor which were
            discarded as invalid."
    ::= { dvmrpNeighborEntry 10 }

dvmrpNeighborRcvBadRoutes OBJECT-TYPE
    SYNTAX     Counter32
    MAX-ACCESS read-only
    STATUS     current
    DESCRIPTION
            "The number of routes, in valid DVMRP packets received from
            this neighbor, which were ignored because the entry was
            invalid."
    ::= { dvmrpNeighborEntry 11 }

dvmrpNeighborState OBJECT-TYPE
    SYNTAX     INTEGER { oneway(1), active(2), ignoring(3), down(4) }
    MAX-ACCESS read-only
    STATUS     current
    DESCRIPTION
            "State of the neighbor adjacency."
    ::= { dvmrpNeighborEntry 12 }


-- The DVMRP Route Table

dvmrpRouteTable OBJECT-TYPE
    SYNTAX     SEQUENCE OF DvmrpRouteEntry
    MAX-ACCESS not-accessible
    STATUS     current
    DESCRIPTION
            "The table of routes learned through DVMRP route exchange."
    ::= { dvmrpMgt 4 }

dvmrpRouteEntry OBJECT-TYPE
    SYNTAX     DvmrpRouteEntry
    MAX-ACCESS not-accessible
    STATUS     current
    DESCRIPTION
            "An entry (conceptual row) containing the multicast routing
            information used by DVMRP in place of unicast routing
            information."
    INDEX      { dvmrpRouteSource, dvmrpRouteSourceMask }
    ::= { dvmrpRouteTable 1 }

DvmrpRouteEntry ::= SEQUENCE {
    dvmrpRouteSource             IpAddress,
    dvmrpRouteSourceMask         IpAddress,
    dvmrpRouteUpstreamNeighbor   IpAddress,
    dvmrpRouteIfIndex            InterfaceIndexOrZero,
    dvmrpRouteMetric             Integer32,
    dvmrpRouteExpiryTime         TimeTicks,
    dvmrpRouteUpTime             TimeTicks
}

dvmrpRouteSource OBJECT-TYPE
    SYNTAX     IpAddress
    MAX-ACCESS not-accessible
    STATUS     current
    DESCRIPTION
            "The network address which when combined with the
            corresponding value of dvmrpRouteSourceMask identifies the
            sources for which this entry contains multicast routing
            information."
    ::= { dvmrpRouteEntry 1 }

dvmrpRouteSourceMask OBJECT-TYPE
    SYNTAX     IpAddress
    MAX-ACCESS not-accessible
    STATUS     current
    DESCRIPTION
            "The network mask which when combined with the corresponding
            value of dvmrpRouteSource identifies the sources for which
            this entry contains multicast routing information."
    ::= { dvmrpRouteEntry 2 }

dvmrpRouteUpstreamNeighbor OBJECT-TYPE
    SYNTAX     IpAddress
    MAX-ACCESS read-only
    STATUS     current
    DESCRIPTION
            "The address of the upstream neighbor (e.g., RPF neighbor)
            from which IP datagrams from these sources are received."
    ::= { dvmrpRouteEntry 3 }

dvmrpRouteIfIndex OBJECT-TYPE
    SYNTAX     InterfaceIndexOrZero
    MAX-ACCESS read-only
    STATUS     current
    DESCRIPTION
            "The value of the ifIndex for the interface on which IP
            datagrams sent by these sources are received. A value of 0
            typically means the route is an aggregate for which no next-
            hop interface exists."
    ::= { dvmrpRouteEntry 4 }

dvmrpRouteMetric OBJECT-TYPE
    SYNTAX     Integer32 (1..32)
    MAX-ACCESS read-only
    STATUS     current
    DESCRIPTION
            "The distance in hops to the source subnet."
    ::= { dvmrpRouteEntry 5 }

dvmrpRouteExpiryTime OBJECT-TYPE
    SYNTAX     TimeTicks
    MAX-ACCESS read-only
    STATUS     current
    DESCRIPTION
            "The minimum amount of time remaining before this entry will
            be aged out."
    ::= { dvmrpRouteEntry 6 }

dvmrpRouteUpTime OBJECT-TYPE
    SYNTAX     TimeTicks
    MAX-ACCESS read-only
    STATUS     current
    DESCRIPTION
            "The time since the route represented by this entry was
            learned by the router."
    ::= { dvmrpRouteEntry 7 }

-- The DVMRP Routing Next Hop Table

dvmrpRouteNextHopTable OBJECT-TYPE
    SYNTAX     SEQUENCE OF DvmrpRouteNextHopEntry
    MAX-ACCESS not-accessible
    STATUS     current
    DESCRIPTION
            "The (conceptual) table containing information on the next
            hops on outgoing interfaces for routing IP multicast
            datagrams."
    ::= { dvmrpMgt 5 }

dvmrpRouteNextHopEntry OBJECT-TYPE
    SYNTAX     DvmrpRouteNextHopEntry
    MAX-ACCESS not-accessible
    STATUS     current
    DESCRIPTION
            "An entry (conceptual row) in the list of next hops on
            outgoing interfaces to which IP multicast datagrams from
            particular sources are routed."
    INDEX      { dvmrpRouteNextHopSource, dvmrpRouteNextHopSourceMask,
                 dvmrpRouteNextHopIfIndex }
    ::= { dvmrpRouteNextHopTable 1 }

DvmrpRouteNextHopEntry ::= SEQUENCE {
    dvmrpRouteNextHopSource             IpAddress,
    dvmrpRouteNextHopSourceMask         IpAddress,
    dvmrpRouteNextHopIfIndex            InterfaceIndex,
    dvmrpRouteNextHopType               INTEGER
}

dvmrpRouteNextHopSource OBJECT-TYPE
    SYNTAX     IpAddress
    MAX-ACCESS not-accessible
    STATUS     current
    DESCRIPTION
            "The network address which when combined with the
            corresponding value of dvmrpRouteNextHopSourceMask
            identifies the sources for which this entry specifies a next
            hop on an outgoing interface."
    ::= { dvmrpRouteNextHopEntry 1 }

dvmrpRouteNextHopSourceMask OBJECT-TYPE
    SYNTAX     IpAddress
    MAX-ACCESS not-accessible
    STATUS     current
    DESCRIPTION
            "The network mask which when combined with the corresponding
            value of dvmrpRouteNextHopSource identifies the sources for
            which this entry specifies a next hop on an outgoing
            interface."
    ::= { dvmrpRouteNextHopEntry 2 }

dvmrpRouteNextHopIfIndex OBJECT-TYPE
    SYNTAX     InterfaceIndex
    MAX-ACCESS not-accessible
    STATUS     current
    DESCRIPTION
            "The ifIndex value of the interface for the outgoing
            interface for this next hop."
    ::= { dvmrpRouteNextHopEntry 3 }

dvmrpRouteNextHopType OBJECT-TYPE
    SYNTAX     INTEGER { leaf(1), branch(2) }
    MAX-ACCESS read-only
    STATUS     current
    DESCRIPTION
            "Type is leaf if no downstream dependent neighbors exist on
            the outgoing virtual interface. Otherwise, type is branch."
    ::= { dvmrpRouteNextHopEntry 4 }

-- The DVMRP Prune Table

dvmrpPruneTable OBJECT-TYPE
    SYNTAX     SEQUENCE OF DvmrpPruneEntry
    MAX-ACCESS not-accessible
    STATUS     current
    DESCRIPTION
            "The (conceptual) table listing the router's upstream prune
            state."
    ::= { dvmrpMgt 6 }

dvmrpPruneEntry OBJECT-TYPE
    SYNTAX     DvmrpPruneEntry
    MAX-ACCESS not-accessible
    STATUS     current
    DESCRIPTION
            "An entry (conceptual row) in the dvmrpPruneTable."
    INDEX      { dvmrpPruneGroup, dvmrpPruneSource,
                 dvmrpPruneSourceMask }
    ::= { dvmrpPruneTable 1 }

DvmrpPruneEntry ::= SEQUENCE {
    dvmrpPruneGroup              IpAddress,
    dvmrpPruneSource             IpAddress,
    dvmrpPruneSourceMask         IpAddress,
    dvmrpPruneExpiryTime         TimeTicks
}

dvmrpPruneGroup OBJECT-TYPE
    SYNTAX     IpAddress
    MAX-ACCESS not-accessible
    STATUS     current
    DESCRIPTION
            "The group address which has been pruned."
    ::= { dvmrpPruneEntry 1 }

dvmrpPruneSource OBJECT-TYPE
    SYNTAX     IpAddress
    MAX-ACCESS not-accessible
    STATUS     current
    DESCRIPTION
            "The address of the source or source network which has been
            pruned."
    ::= { dvmrpPruneEntry 2 }

dvmrpPruneSourceMask OBJECT-TYPE
    SYNTAX     IpAddress
    MAX-ACCESS not-accessible
    STATUS     current
    DESCRIPTION
            "The address of the source or source network which has been
            pruned. The mask must either be all 1's, or else
            dvmrpPruneSource and dvmrpPruneSourceMask must match
            dvmrpRouteSource and dvmrpRouteSourceMask for some entry in
            the dvmrpRouteTable."
    ::= { dvmrpPruneEntry 3 }

dvmrpPruneExpiryTime OBJECT-TYPE
    SYNTAX     TimeTicks
    MAX-ACCESS read-only
    STATUS     current
    DESCRIPTION
            "The amount of time remaining before this prune should
            expire at the upstream neighbor. This value should be the
            minimum of the default prune lifetime and the remaining
            prune lifetimes of the local router's downstream neighbors,
            if any."
    ::= { dvmrpPruneEntry 4 }

--
-- routeMgt
--
ipIrdpTable OBJECT-TYPE
        SYNTAX      SEQUENCE OF IpIrdpEntry
        MAX-ACCESS  not-accessible
        STATUS      current
        DESCRIPTION "A list of IP IRDP status."
        ::= { routeMgt 1 }

ipIrdpEntry OBJECT-TYPE
        SYNTAX      IpIrdpEntry
        MAX-ACCESS  not-accessible
        STATUS      current
        DESCRIPTION "An entry in the table, containing information
                     about IP IRDP configuration."
        INDEX       { ipIrdpIfIndex }
        ::= { ipIrdpTable 1 }

IpIrdpEntry ::= SEQUENCE
{
    ipIrdpIfIndex                   Integer32,
    ipIrdpProcessStatus             EnabledStatus,
    ipIrdpAdvertisementAddress      INTEGER,
    ipIrdpMaxAdvertisementInterval  Integer32,
    ipIrdpMinAdvertisementInterval  Integer32,
    ipIrdpAdvertisementLifetime     Integer32,
    ipIrdpPreferenceLevel           Integer32
}

ipIrdpIfIndex OBJECT-TYPE
        SYNTAX      Integer32
        MAX-ACCESS  not-accessible
        STATUS      current
        DESCRIPTION "This is defined as a VLAN interface.
                     A routing interface is a VLAN that binds an IP subnet."
        ::= { ipIrdpEntry 1 }

ipIrdpProcessStatus OBJECT-TYPE
        SYNTAX      EnabledStatus
        MAX-ACCESS  read-write
        STATUS      current
        DESCRIPTION "Enable or Disable IP IRDP process on an interface."
        DEFVAL      { disabled }
        ::= { ipIrdpEntry 2 }

ipIrdpAdvertisementAddress OBJECT-TYPE
        SYNTAX      INTEGER
                    {
                        multicast(1),
                        broadcast(2)
                    }
        MAX-ACCESS  read-write
        STATUS      current
        DESCRIPTION "The IP destination address to be used for multicast
                     Router Advertisements sent from the interface. The
                     only permissible values are the all-systems multicast
                     address, 224.0.0.1, or the limited-broadcast address,
                     255.255.255.255. (The all-systems address is preferred
                     wherever possible, i.e., on any link where all
                     listening hosts support IP multicast.)"
        DEFVAL      { broadcast }
        ::= { ipIrdpEntry 3 }

ipIrdpMaxAdvertisementInterval OBJECT-TYPE
        SYNTAX      Integer32 (4..1800)
        MAX-ACCESS  read-write
        STATUS      current
        DESCRIPTION "The maximum time allowed between sending multicast
                     Router Advertisements from the interface, in seconds.
                     Must be no less than 4 seconds and no greater than 1800
                     seconds."
        DEFVAL      { 600 }
        ::= { ipIrdpEntry 4 }

ipIrdpMinAdvertisementInterval OBJECT-TYPE
        SYNTAX      Integer32 (3..1800)
        MAX-ACCESS  read-write
        STATUS      current
        DESCRIPTION "The minimum time allowed between sending unsolicited
                 multicast Router Advertisements from the interface, in
                 seconds.  Must be no less than 3 seconds and no greater
                 than MaxAdvertisementInterval. It default value is 0.75*
                 the value of ipIrdpMaxAdvertisementInterval."
        ::= { ipIrdpEntry 5 }

ipIrdpAdvertisementLifetime OBJECT-TYPE
        SYNTAX      Integer32 (4..9000)
        MAX-ACCESS  read-write
        STATUS      current
        DESCRIPTION "The value to be placed in the Lifetime field of Router
                     Advertisements sent from the interface, in seconds.
                     Must be no less than MaxAdvertisementInterval and no
                     greater than 9000 seconds. Its default is 3 times
                     the value of the ipIrdpMaxAdvertisementInterval."
        ::= { ipIrdpEntry 6 }

ipIrdpPreferenceLevel OBJECT-TYPE
        SYNTAX      Integer32
        MAX-ACCESS  read-write
        STATUS      current
        DESCRIPTION "The preferability of the address as a default router
                        address, relative to other router addresses on the same
                        subnet. A 32-bit, signed, integer, where negative numbers are
                represented in twos-complement form, with higher values meaning
                        more preferable. The minimum value (hex 80000000) is used
                        to indicate that the address, even though it may be
                        advertised, is not to be used by neighboring hosts as a default
                        router address."
        DEFVAL      { 0 }
        ::= { ipIrdpEntry 7 }

ipCidrRouteExtTable OBJECT-TYPE
    SYNTAX   SEQUENCE OF IpCidrRouteExtEntry
    MAX-ACCESS not-accessible
    STATUS   current
    DESCRIPTION
       "This entity's IP Extension Routing table."
    REFERENCE
        "Rfc2096 Section 9, IP CIDR Route Table."
    ::= { routeMgt 2 }

ipCidrRouteExtEntry OBJECT-TYPE
    SYNTAX   IpCidrRouteExtEntry
    MAX-ACCESS not-accessible
    STATUS   current
    DESCRIPTION
       "A particular route to a particular destination,
            under a particular policy."
    INDEX {
        ipCidrRouteExtDest,
        ipCidrRouteExtMask,
        ipCidrRouteExtTos,
        ipCidrRouteExtNextHop
        }
    ::= { ipCidrRouteExtTable 1 }

IpCidrRouteExtEntry ::=
    SEQUENCE {
        ipCidrRouteExtDest
            IpAddress,
        ipCidrRouteExtMask
            IpAddress,
        ipCidrRouteExtTos
             Integer32,
        ipCidrRouteExtNextHop
            IpAddress,
        ipCidrRouteExtOspfSubType
            INTEGER
    }

ipCidrRouteExtDest OBJECT-TYPE
    SYNTAX   IpAddress
    MAX-ACCESS not-accessible
    STATUS   current
    DESCRIPTION
       "The destination IP address of this route.

       This object may not take a Multicast (Class D)
       address value.

       Any assignment (implicit or otherwise) of an
       instance of this object to a value x must be
       rejected if the bitwise logical-AND of x with
       the value of the corresponding instance of the
       ipCidrRouteMask object is not equal to x."
    ::= { ipCidrRouteExtEntry 1 }

ipCidrRouteExtMask OBJECT-TYPE
    SYNTAX   IpAddress
    MAX-ACCESS not-accessible
    STATUS   current
    DESCRIPTION
       "Indicates the mask to be logically-ANDed with the
            destination address before being compared to
            the value in the ipCidrRouteDest field. For
            those systems that do not support arbitrary
            subnet masks, an agent constructs the value  of
            the ipCidrRouteMask by reference to the IP Address Class.


            Any assignment (implicit or otherwise) of an
            instance of this object to a value x must be
            rejected if the bitwise logical-AND of x with
            the value of the corresponding instance of the
         ipCidrRouteDest object is not equal to
         ipCidrRoute-Dest."
    ::= { ipCidrRouteExtEntry 2 }

-- The following convention is included for specification
-- of TOS Field contents.  At this time, the Host Requirements
-- and the Router Requirements documents disagree on the width
-- of the TOS field.  This mapping describes the Router
-- Requirements mapping, and leaves room to widen the TOS field
-- without impact to fielded systems.

ipCidrRouteExtTos OBJECT-TYPE
    SYNTAX   Integer32
    MAX-ACCESS not-accessible
    STATUS   current
    DESCRIPTION
       "The policy specifier is the IP TOS Field. The encoding
            of IP TOS is as specified by the following convention.
            Zero indicates the default path if no more  specific
            policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30"
    ::= { ipCidrRouteExtEntry 3 }

ipCidrRouteExtNextHop OBJECT-TYPE
    SYNTAX   IpAddress
    MAX-ACCESS not-accessible
    STATUS   current
    DESCRIPTION
       "On remote routes, the address of the next system en route;
Otherwise, 0.0.0.0."
    ::= { ipCidrRouteExtEntry 4 }

ipCidrRouteExtOspfSubType OBJECT-TYPE
    SYNTAX   INTEGER
             {
              none(1),
              ospfInter(2),
              ospfIntra(3),
              ospfNssa1(4),
              ospfNssa2(5),
              ospfType1(6),
              ospfType2(7)
             }
    MAX-ACCESS read-only
    STATUS   current
    DESCRIPTION
       "The OSPF SubType, when the ipCidrRouteProto in IP-FORWARD MIB is
        ospf(13), this object has the value (2)-(7), otherwises, this object
        will always show none(1)."
    REFERENCE " Rfc2096 Section 9, IP CIDR Route Table."
    ::= { ipCidrRouteExtEntry 5 }

--
-- sysLogMgt
--

-- Management for system log. This configures the logging
-- of events inside the switch.

sysLogStatus OBJECT-TYPE
        SYNTAX      EnabledStatus
        MAX-ACCESS  read-write
        STATUS      current
        DESCRIPTION "Whether the system log is enabled."
        ::= { sysLogMgt 1 }

sysLogHistoryFlashLevel OBJECT-TYPE
        SYNTAX      Integer32 (0..7)
        MAX-ACCESS  read-write
        STATUS      current
        DESCRIPTION "Severity level for logging to flash."
        ::= { sysLogMgt 2 }

sysLogHistoryRamLevel OBJECT-TYPE
        SYNTAX      Integer32 (0..7)
        MAX-ACCESS  read-write
        STATUS      current
        DESCRIPTION "Severity level for logging to RAM."
        ::= { sysLogMgt 3 }

sysLogLoggingInterval OBJECT-TYPE
        SYNTAX      Integer32
        MAX-ACCESS  read-write
        STATUS      current
        DESCRIPTION "The logging interval of the log system in minutes."
        ::= { sysLogMgt 4 }

sysLogLoggingCount OBJECT-TYPE
        SYNTAX      Integer32
        MAX-ACCESS  read-write
        STATUS      current
        DESCRIPTION "The logging count of the log system."
        ::= { sysLogMgt 5 }

--
--remoteLogMgt
--

remoteLogMgt OBJECT IDENTIFIER ::= { sysLogMgt 6 }

remoteLogStatus OBJECT-TYPE
       SYNTAX      EnabledStatus
       MAX-ACCESS  read-write
       STATUS      current
       DESCRIPTION "Whether the remote log system is enabled."
       ::= { remoteLogMgt 1 }

remoteLogLevel OBJECT-TYPE
        SYNTAX      Integer32 (0..7)
        MAX-ACCESS  read-write
        STATUS      current
        DESCRIPTION "Severity level for remote log."
        ::= { remoteLogMgt 2 }

remoteLogFacilityType OBJECT-TYPE
        SYNTAX      INTEGER
                    {
                      localUse0(16),
                      localUse1(17),
                      localUse2(18),
                      localUse3(19),
                      localUse4(20),
                      localUse5(21),
                      localUse6(22),
                      localUse7(23)
                     }
        MAX-ACCESS   read-write
        STATUS       current
        DESCRIPTION " The facility type for remote log."
        ::= { remoteLogMgt 3 }

--remoteLogServerTable

remoteLogServerTable OBJECT-TYPE
        SYNTAX      SEQUENCE OF RemoteLogServerEntry
        MAX-ACCESS  not-accessible
        STATUS      current
        DESCRIPTION "A Table for storing the remote log Server list."
        ::= { remoteLogMgt 4 }

remoteLogServerEntry OBJECT-TYPE
        SYNTAX      RemoteLogServerEntry
        MAX-ACCESS  not-accessible
        STATUS      current
        DESCRIPTION "A conceptual row for remoteLogServerTable."
        INDEX { remoteLogServerIp }
        ::= { remoteLogServerTable 1 }

RemoteLogServerEntry ::= SEQUENCE
{
    remoteLogServerIp     IpAddress,
    remoteLogServerStatus ValidStatus
}

remoteLogServerIp OBJECT-TYPE
         SYNTAX      IpAddress
         MAX-ACCESS  not-accessible
         STATUS      current
         DESCRIPTION "The IP address of the remote log Server."
         ::= { remoteLogServerEntry 1 }

remoteLogServerStatus OBJECT-TYPE
         SYNTAX      ValidStatus
         MAX-ACCESS  read-create
         STATUS      current
         DESCRIPTION  "Setting this to valid(1) creates an entry.
                       Setting this to invalid(2) destroys an entry."
         ::= { remoteLogServerEntry 2 }

--remoteLogServerHostTable

remoteLogServerHostTable OBJECT-TYPE
        SYNTAX      SEQUENCE OF RemoteLogServerHostEntry
        MAX-ACCESS  not-accessible
        STATUS      current
        DESCRIPTION "A Table for storing the remote log Server list."
        ::= { remoteLogMgt 5 }

remoteLogServerHostEntry OBJECT-TYPE
        SYNTAX      RemoteLogServerHostEntry
        MAX-ACCESS  not-accessible
        STATUS      current
        DESCRIPTION "A conceptually row for remoteLogServerHostTable."
        INDEX { remoteLogServerHostName }
        ::= { remoteLogServerHostTable 1 }

RemoteLogServerHostEntry ::= SEQUENCE
{
    remoteLogServerHostName     DisplayString,
    remoteLogServerHostStatus       ValidStatus
}

remoteLogServerHostName OBJECT-TYPE
         SYNTAX      DisplayString(SIZE(0..255))
         MAX-ACCESS  not-accessible
         STATUS      current
         DESCRIPTION "The IP address or DNS of the remote log Server."
         ::= { remoteLogServerHostEntry 1 }

remoteLogServerHostStatus OBJECT-TYPE
         SYNTAX      ValidStatus
         MAX-ACCESS  read-create
         STATUS      current
         DESCRIPTION  "Setting this to valid(1) creates an entry.
                       Setting this to invalid(2) destroys an entry."
         ::= { remoteLogServerHostEntry 2 }

--remoteLogHostTable

remoteLogHostTable OBJECT-TYPE
        SYNTAX      SEQUENCE OF RemoteLogHostEntry
        MAX-ACCESS  not-accessible
        STATUS      current
        DESCRIPTION
            "A table/list recording the remote log hosts."
        ::= { remoteLogMgt 6 }

remoteLogHostEntry OBJECT-TYPE
        SYNTAX      RemoteLogHostEntry
        MAX-ACCESS  not-accessible
        STATUS      current
        DESCRIPTION
            "A conceptual row for remoteLogHostTable."
        INDEX { remoteLogHostId }
        ::= { remoteLogHostTable 1 }

RemoteLogHostEntry ::= SEQUENCE
{
    remoteLogHostId                 Unsigned32,
    remoteLogHostInetAddressType    InetAddressType,
    remoteLogHostInetAddress        InetAddress,
    remoteLogHostFacilityType       INTEGER,
    remoteLogHostLevel              Unsigned32,
    remoteLogHostStatus             ValidStatus
}

remoteLogHostId OBJECT-TYPE
        SYNTAX      Unsigned32
        MAX-ACCESS  not-accessible
        STATUS      current
        DESCRIPTION
            "The remote log host ID."
        ::= { remoteLogHostEntry 1 }

remoteLogHostInetAddressType OBJECT-TYPE
        SYNTAX      InetAddressType
        MAX-ACCESS  read-create
        STATUS      current
        DESCRIPTION
            "The Internet address types used by remoteLogHostEntry. This
             object is limited to ipv4(1) address."
        ::= { remoteLogHostEntry 2 }

remoteLogHostInetAddress OBJECT-TYPE
        SYNTAX      InetAddress
        MAX-ACCESS  read-create
        STATUS      current
        DESCRIPTION
            "The Internet address of the remote log host."
        ::= { remoteLogHostEntry 3 }

remoteLogHostFacilityType OBJECT-TYPE
        SYNTAX      INTEGER
                    {
                      localUse0(16),
                      localUse1(17),
                      localUse2(18),
                      localUse3(19),
                      localUse4(20),
                      localUse5(21),
                      localUse6(22),
                      localUse7(23)
                     }
        MAX-ACCESS   read-create
        STATUS       current
        DESCRIPTION
            "The facility type of the remote log host."
        ::= { remoteLogHostEntry 4 }

remoteLogHostLevel  OBJECT-TYPE
        SYNTAX      Unsigned32(0..7)
        MAX-ACCESS  read-create
        STATUS      current
        DESCRIPTION
            "The severity level of the remote log host."
        ::= { remoteLogHostEntry 5 }

remoteLogHostStatus OBJECT-TYPE
        SYNTAX      ValidStatus
        MAX-ACCESS  read-create
        STATUS      current
        DESCRIPTION
            "Setting this to valid(1) creates an entry.
             Setting this to invalid(2) destroys an entry."
        ::= { remoteLogHostEntry 6 }

--
--smtpMgt
--
smtpMgt   OBJECT IDENTIFIER ::= { sysLogMgt 7 }

smtpStatus OBJECT-TYPE
    SYNTAX       EnabledStatus
    MAX-ACCESS   read-write
    STATUS       current
    DESCRIPTION "Set enabled(1) to enable the SMTP, set disabled(2) to disable
                 the SMTP."
    ::= { smtpMgt 1 }

smtpSeverityLevel OBJECT-TYPE
    SYNTAX       Integer32 (0..7)
    MAX-ACCESS   read-write
    STATUS       current
    DESCRIPTION "Specify the SMTP minimum severity level to send the event message."
    ::= { smtpMgt 2 }

smtpSourceEMail OBJECT-TYPE
    SYNTAX       DisplayString (SIZE(0..41))
    MAX-ACCESS   read-write
    STATUS       current
    DESCRIPTION "SMTP source email address,
                 the sender's mail address that appears
                 in the 'From' field of the mail."
    ::= { smtpMgt 3 }

--smtpServerIpTable

smtpServerIpTable OBJECT-TYPE
       SYNTAX      SEQUENCE OF SmtpServerIpEntry
       MAX-ACCESS  not-accessible
       STATUS      current
       DESCRIPTION "The SMTP server IP table.
                    The maximum servers to be added is 3."
       ::= { smtpMgt 4 }

smtpServerIpEntry OBJECT-TYPE
       SYNTAX      SmtpServerIpEntry
       MAX-ACCESS  not-accessible
       STATUS      current
       DESCRIPTION "A conceptual row of the smtpServerIpTable."
       INDEX  { smtpServerIp }
       ::= { smtpServerIpTable 1 }

SmtpServerIpEntry ::= SEQUENCE
{
    smtpServerIp     IpAddress,
    smtpServerIpStatus ValidStatus
}

smtpServerIp OBJECT-TYPE
       SYNTAX      IpAddress
       MAX-ACCESS  accessible-for-notify
       STATUS      current
       DESCRIPTION "SMTP mail server's IP address."
       ::= { smtpServerIpEntry 1 }

smtpServerIpStatus OBJECT-TYPE
       SYNTAX      ValidStatus
       MAX-ACCESS  read-create
       STATUS      current
       DESCRIPTION "Setting this to valid(1) creates an entry.
                    Setting this to invalid(2) destroys an entry."
       ::= { smtpServerIpEntry 2 }

--smtpDestEMailTable

smtpDestEMailTable OBJECT-TYPE
       SYNTAX      SEQUENCE OF SmtpDestEMailEntry
       MAX-ACCESS  not-accessible
       STATUS      current
       DESCRIPTION "The table of the destination e-mail address.
                    The maximum numbers of destination email address to be added is 5."
       ::= { smtpMgt 5}

smtpDestEMailEntry OBJECT-TYPE
       SYNTAX      SmtpDestEMailEntry
       MAX-ACCESS  not-accessible
       STATUS      current
       DESCRIPTION "A conceptual row of the smtpDestEMailTable."
       INDEX  { smtpDestEMail }
       ::= { smtpDestEMailTable 1 }

SmtpDestEMailEntry ::= SEQUENCE
{
    smtpDestEMail     DisplayString,
    smtpDestEMailStatus ValidStatus
}

smtpDestEMail OBJECT-TYPE
       SYNTAX      DisplayString (SIZE(0..41))
       MAX-ACCESS  not-accessible
       STATUS      current
       DESCRIPTION "SMTP destination e-mail address."
       ::= { smtpDestEMailEntry 1 }

smtpDestEMailStatus OBJECT-TYPE
       SYNTAX      ValidStatus
       MAX-ACCESS  read-create
       STATUS      current
       DESCRIPTION "Setting this to valid(1) creates an entry.
                    Setting this to invalid(2) destroys an entry."
       ::= { smtpDestEMailEntry 2 }

--smtpServerHostTable

smtpServerHostTable OBJECT-TYPE
       SYNTAX      SEQUENCE OF SmtpServerHostEntry
       MAX-ACCESS  not-accessible
       STATUS      current
       DESCRIPTION "The SMTP server table.
                    The maximum servers to be added is 3."
       ::= { smtpMgt 6 }

smtpServerHostEntry OBJECT-TYPE
       SYNTAX      SmtpServerHostEntry
       MAX-ACCESS  not-accessible
       STATUS      current
       DESCRIPTION "A conceptual row of the smtpServerHostTable."
       INDEX  { smtpServerHostName }
       ::= { smtpServerHostTable 1 }

SmtpServerHostEntry ::= SEQUENCE
{
    smtpServerHostName     DisplayString,
    smtpServerHostStatus ValidStatus
}

smtpServerHostName OBJECT-TYPE
       SYNTAX      DisplayString(SIZE(0..255))
       MAX-ACCESS  not-accessible
       STATUS      current
       DESCRIPTION "IP address or DNS of SMTP mail servers."
       ::= { smtpServerHostEntry 1 }

smtpServerHostStatus OBJECT-TYPE
       SYNTAX      ValidStatus
       MAX-ACCESS  read-create
       STATUS      current
       DESCRIPTION "Setting this to valid(1) creates an entry.
                    Setting this to invalid(2) destroys an entry."
       ::= { smtpServerHostEntry 2 }

--sysLogRamTable

sysLogRamTable OBJECT-TYPE
        SYNTAX      SEQUENCE OF SysLogRamEntry
        MAX-ACCESS  not-accessible
        STATUS      current
        DESCRIPTION "Table for sysLog which is stored in RAM. When we
                     perform a GetFirst operation (GetNext at the sysLogRamTable or
                     the nearest precedence 's node of this MIB variable),
                     this table will created a snapshot record. Then the user can
                     perform the getNext operation repeatly to get the whole record of
                     this snapshot. Note that a snapshot of the record
                     will be created every time when performing the getFirst operation"
        ::= { sysLogMgt 8 }

sysLogRamEntry OBJECT-TYPE
        SYNTAX      SysLogRamEntry
        MAX-ACCESS  not-accessible
        STATUS      current
        DESCRIPTION "Entry for sysLog which stored in RAM."
        INDEX       { sysLogRamIndex }
        ::= { sysLogRamTable 1 }

SysLogRamEntry ::= SEQUENCE
{
    sysLogRamIndex      Integer32,
    sysLogRamLevel      Integer32,
    sysLogRamModule     Integer32,
    sysLogRamFunctionID Integer32,
    sysLogRamErrorID    Integer32,
    sysLogRamTime       DisplayString,
    sysLogRamMessage    DisplayString
}


sysLogRamIndex OBJECT-TYPE
    SYNTAX      Integer32
    MAX-ACCESS  not-accessible
    STATUS      current
    DESCRIPTION "The index of the sysLogRamEntry."
    ::= { sysLogRamEntry 1 }


sysLogRamLevel OBJECT-TYPE
    SYNTAX      Integer32(0..7)
    MAX-ACCESS  read-only
    STATUS      current
    DESCRIPTION "The level of the sysLog, (0) is the highest level and
                 (7) is the lowest level."
    ::= { sysLogRamEntry 2 }

sysLogRamModule OBJECT-TYPE
    SYNTAX      Integer32
    MAX-ACCESS  read-only
    STATUS      current
    DESCRIPTION "The module ID of this log.
                 For detailed information of this module ID,
                 please reference the user manual."
    ::= { sysLogRamEntry 3 }

sysLogRamFunctionID OBJECT-TYPE
    SYNTAX      Integer32
    MAX-ACCESS  read-only
    STATUS      current
    DESCRIPTION "The function ID of the module. This depends on the module."
    ::= { sysLogRamEntry 4 }

sysLogRamErrorID OBJECT-TYPE
    SYNTAX      Integer32
    MAX-ACCESS  read-only
    STATUS      current
    DESCRIPTION "The Error ID of the module. This is module dependent."
    ::= { sysLogRamEntry 5 }

sysLogRamTime OBJECT-TYPE
     SYNTAX      DisplayString(SIZE(20))
     MAX-ACCESS  read-only
     STATUS      current
     DESCRIPTION "The logging time of this log entry. This is a text string in
                  the following form, based on Unix: 'Mmm _d hh:mm:ss yyyy'.
                  'Mmm' is the first three letters of the English name
                  of the month. '_d' is the day of month. A single-digit day
                  is preceded by a space. 'hh:mm:ss' is a 24-hour
                  representations of hours, minutes, and seconds.
                  A single-digit hour is preceded by a zero. 'yyyy' is a
                  four-digit year. An example is: 'Jan  1 02:03:04 2002'."
     ::= { sysLogRamEntry 6 }

sysLogRamMessage OBJECT-TYPE
     SYNTAX      DisplayString(SIZE(1..56))
     MAX-ACCESS  read-only
     STATUS      current
     DESCRIPTION "The description message of this log entry."
     ::= { sysLogRamEntry 7 }


--sysLogFlashTable

sysLogFlashTable OBJECT-TYPE
        SYNTAX      SEQUENCE OF SysLogFlashEntry
        MAX-ACCESS  not-accessible
        STATUS      current
        DESCRIPTION "Table for sysLog which is stored in flash. When we
                     perform a GetFirst operation (GetNext at the sysLogFlashTable or
                     the nearest precedence 's node of this MIB variable),
                     this table will create a snapshot record. Then the user can
                     perform getNext 's operation repeatly to get the whole record of
                     this snapshot. Note that a snapshot of the record
                     will be created everytime when performing a getFirst opration."
        ::= { sysLogMgt 9 }

sysLogFlashEntry OBJECT-TYPE
        SYNTAX      SysLogFlashEntry
        MAX-ACCESS  not-accessible
        STATUS      current
        DESCRIPTION "Entry for sysLog which stored in flash."
        INDEX       { sysLogFlashIndex }
        ::= { sysLogFlashTable 1 }

SysLogFlashEntry ::= SEQUENCE
{
    sysLogFlashIndex      Integer32,
    sysLogFlashLevel      Integer32,
    sysLogFlashModule     Integer32,
    sysLogFlashFunctionID Integer32,
    sysLogFlashErrorID    Integer32,
    sysLogFlashTime       DisplayString,
    sysLogFlashMessage    DisplayString
}


sysLogFlashIndex OBJECT-TYPE
    SYNTAX      Integer32
    MAX-ACCESS  not-accessible
    STATUS      current
    DESCRIPTION "The index of the sysLogFlashEntry."
    ::= { sysLogFlashEntry 1 }


sysLogFlashLevel OBJECT-TYPE
    SYNTAX      Integer32(0..7)
    MAX-ACCESS  read-only
    STATUS      current
    DESCRIPTION "The level of the sysLog, (0) is the highest level and
                 (7) is the lowest level."
    ::= { sysLogFlashEntry 2 }

sysLogFlashModule OBJECT-TYPE
    SYNTAX      Integer32
    MAX-ACCESS  read-only
    STATUS      current
    DESCRIPTION "The module ID of this log. For detailed information of this
                 module ID mapping, please reference the user manual."
    ::= { sysLogFlashEntry 3 }

sysLogFlashFunctionID OBJECT-TYPE
    SYNTAX      Integer32
    MAX-ACCESS  read-only
    STATUS      current
    DESCRIPTION "The function ID of the module. This is dependent on the module."
    ::= { sysLogFlashEntry 4 }

sysLogFlashErrorID OBJECT-TYPE
    SYNTAX      Integer32
    MAX-ACCESS  read-only
    STATUS      current
    DESCRIPTION "The Error ID of the module. This is dependent on the module."
    ::= { sysLogFlashEntry 5 }

sysLogFlashTime OBJECT-TYPE
     SYNTAX      DisplayString(SIZE(20))
     MAX-ACCESS  read-only
     STATUS      current
     DESCRIPTION "The logging time of this log entry. It is a text string in
                  the following form, based on Unix: 'Mmm _d hh:mm:ss yyyy'.
                  'Mmm' is the first three letters of the English name
                  of the month. '_d' is the day of month. A single-digit day
                  is preceded by the space. 'hh:mm:ss' is a 24-hour
                  representations of hours, minutes, and seconds.
                  A single-digit hour is preceded by a zero. 'yyyy' is a
                  four-digit year. An example is: 'Jan  1 02:03:04 2002'."
     ::= { sysLogFlashEntry 6 }

sysLogFlashMessage OBJECT-TYPE
     SYNTAX      DisplayString(SIZE(1..56))
     MAX-ACCESS  read-only
     STATUS      current
     DESCRIPTION "The description message of this log entry."
     ::= { sysLogFlashEntry 7 }

--
-- lineMgt
--

-- Management for line. This includes management for
-- serial line (RS232 port) and Telnet.

consoleMgt           OBJECT IDENTIFIER ::= { lineMgt 1 }
telnetMgt            OBJECT IDENTIFIER ::= { lineMgt 2 }


--consoleMgt

consoleDataBits OBJECT-TYPE
        SYNTAX      INTEGER
                    {
                      databits7(1),
                      databits8(2)
                    }
        MAX-ACCESS  read-write
        STATUS      current
        DESCRIPTION "Number of data bits."
        ::= { consoleMgt 1 }

consoleParity OBJECT-TYPE
        SYNTAX      INTEGER
                    {
                     partyNone(1),
                     partyEven(2),
                     partyOdd(3)
                    }
        MAX-ACCESS  read-write
        STATUS      current
        DESCRIPTION "Defines the generation of a parity bit."
        ::= { consoleMgt 2 }

consoleBaudRate OBJECT-TYPE
        SYNTAX      INTEGER
                    {
                     baudRate9600(1),
                     baudRate19200(2),
                     baudRate38400(3),
                     baudRate57600(4),
                     baudRate115200(5)
                    }
        MAX-ACCESS  read-write
        STATUS      current
        DESCRIPTION "Baud rate: Valid values are 115200, 57600, 38400,
                     19200, and 9600."
        ::= { consoleMgt 3 }

consoleStopBits OBJECT-TYPE
        SYNTAX     INTEGER
                   {
                    stopbits1(1),
                    stopbits2(2)
                   }
        MAX-ACCESS read-write
        STATUS     current
        DESCRIPTION "The console stop bits, valid values are stopbits1(1) or stopbits2(2)"
        ::= { consoleMgt 4 }

consoleExecTimeout OBJECT-TYPE
        SYNTAX      Integer32 (0..65535)
        MAX-ACCESS  read-write
        STATUS      current
        DESCRIPTION "In a serial console, use the consoleExecTimeout
                     variable to set the interval that the EXEC command
                     interpreter waits until user input is detected;
                     set the value to 0 to disable it."
        ::= { consoleMgt 5 }

consolePasswordThreshold OBJECT-TYPE
        SYNTAX      Integer32 (0..120)
        MAX-ACCESS  read-write
        STATUS      current
        DESCRIPTION "The number of failed console logon attempts that may be
                     made before the system will not accept a further attempt
                     in the time specified by consoleSilentTime. A value of 0
                     disables the functionality."
        ::= { consoleMgt 6 }

consoleSilentTime OBJECT-TYPE
        SYNTAX      Integer32 (0..65535)
        MAX-ACCESS  read-write
        STATUS      current
        DESCRIPTION "The length of time that the management console is
                     inaccessible after the number of failed logon
                     attempts has reached consolePasswordThreshold. A value
                     of 0 disables the functionality."

        ::= { consoleMgt 7 }

consoleAdminBaudRate OBJECT-TYPE
        SYNTAX      Integer32
        MAX-ACCESS  read-write
        STATUS      current
        DESCRIPTION "Baud rate. Valid values are 2400, 4800, 9600,
                    19200, 38400, 57600, 115200.

                    Setting this variable to 0 means autobaud.
                    Please read the actual baud rate in the consoleOperBaudRate variable."
        ::= { consoleMgt 8 }

consoleOperBaudRate OBJECT-TYPE
        SYNTAX      Integer32
        MAX-ACCESS  read-only
        STATUS      current
        DESCRIPTION "The baud rate currently in use."
        ::= { consoleMgt 9 }

--to set login timeout seconds
consoleLoginResponseTimeout OBJECT-TYPE
        SYNTAX      Integer32(0..300)
        MAX-ACCESS  read-write
        STATUS      current
        DESCRIPTION  "Console login response timeout setting.
                     Valid range is 0 to 300. Setting to 0 means disabled."
        ::= { consoleMgt 10 }

-- telnetMgt

telnetExecTimeout OBJECT-TYPE
        SYNTAX      Integer32 (1..65535)
        MAX-ACCESS  read-write
        STATUS      current
        DESCRIPTION  "Specifies the interval that the system waits for user input
                      before terminating the current telnet session."
        ::= { telnetMgt 1 }

telnetPasswordThreshold OBJECT-TYPE
        SYNTAX      Integer32 (0..120)
        MAX-ACCESS  read-write
        STATUS      current
        DESCRIPTION "The number of failed telnet logon attempts that may be made
                     before the system will not accept a further attempt to logon
                     with telnet."
        ::= { telnetMgt 2 }

--to set login timeout seconds
telnetLoginResponseTimeout OBJECT-TYPE
        SYNTAX      Integer32(1..300)
        MAX-ACCESS  read-write
        STATUS      current
        DESCRIPTION  "Telnet login response timeout setting.
                     Valid range is 1 to 300.
                     This timout setting cannot be disbled."
        ::= { telnetMgt 3 }

telnetStatus OBJECT-TYPE
        SYNTAX      EnabledStatus
        MAX-ACCESS  read-write
        STATUS      current
        DESCRIPTION "To enable or disable the telnet function.
                Any new telnet request will be rejected and all current telnet sessions will be
                    terminated if this status is set to disabled(2)."
        DEFVAL { enabled }
        ::= { telnetMgt 4 }

telnetPortNumber OBJECT-TYPE
        SYNTAX      Integer32 (1..65535)
        MAX-ACCESS  read-write
        STATUS      current
        DESCRIPTION "The telnet session port number."
        DEFVAL { 23 }
        ::= { telnetMgt 5 }

--
--bladeMgt
--

-- Managemnt for blades in a multiblade system.
-- Each blade is an individual switch.

bladeIndex OBJECT-TYPE
         SYNTAX             Integer32(1..16)
         MAX-ACCESS         read-write
         STATUS             current
         DESCRIPTION        "This indicates which blade in the multi-switch system is currently
                             managing."
         ::= { bladeMgt 1 }

bladeType OBJECT-TYPE
         SYNTAX       INTEGER
                      {
                         other(1),
                         bbm6208(2),
                         bbm6216(3)

                       }
          MAX-ACCESS  read-only
          STATUS      current
          DESCRIPTION "This variable indicates the type of the CMC."
          ::= { bladeMgt 2 }

bladeCopyMgt OBJECT IDENTIFIER ::= { bladeMgt 3 }

bladeCopyFileName  OBJECT-TYPE
    SYNTAX     DisplayString (SIZE(0..127))
    MAX-ACCESS read-write
    STATUS     current
    DESCRIPTION
        "The source file name for copy transfer when a
        transfer is next requested via this MIB. This value is set to
        a zero length string when no file name has been specified."
    ::= { bladeCopyMgt 1 }

bladeCopyDestBlade  OBJECT-TYPE
    SYNTAX     Integer32 (1..16)
    MAX-ACCESS read-write
    STATUS     current
    DESCRIPTION
        "The destination blade to which we want to copy. Set to 101 to
         copy to all blades."
    ::= { bladeCopyMgt 2 }

bladeCopyAction OBJECT-TYPE
    SYNTAX     INTEGER
               {
                 noCopy(1),
                 copy(2)
               }
    MAX-ACCESS read-write
    STATUS     current
    DESCRIPTION
         "Set copy(2) to begin to copy. When not copying,
          return noCopy(1)."
    ::= { bladeCopyMgt 3 }

bladeCopyStatus  OBJECT-TYPE
    SYNTAX     INTEGER {
                    copySuccess(1),
                    copyStatusUnknown(2),
                    copyGeneralError(3)
                    }
    MAX-ACCESS read-only
    STATUS     current
    DESCRIPTION
        "The status of the last transfer procedure, if any. This
        will have a value of copyStatusUnknown(2) if no
        transfer process has been performed."
    ::= { bladeCopyMgt 4 }

bladeCopySuccessList  OBJECT-TYPE
    SYNTAX    OCTET STRING
    MAX-ACCESS read-only
    STATUS     current
    DESCRIPTION
        "When performing the copy to all blades action (set bladeCopyDestBlade to 101),
         this variable shows the byte list of success blades,
          the highest bit of the first byte means blade 0."
    ::= { bladeCopyMgt 5 }

bladeCopyFailureList  OBJECT-TYPE
    SYNTAX    OCTET STRING
    MAX-ACCESS read-only
    STATUS     current
    DESCRIPTION
       "When performing the copy to all blades action (set bladeCopyDestBlade to 101),
         this variable shows the byte list of failure blades, the highest bit of
         of the first byte means blade 0."
    ::= { bladeCopyMgt 6 }

--
-- ftthMgt
--

-- Managemnt for Fibre to the Home (FTTH).

ftthUtpMgt OBJECT IDENTIFIER ::= { ftthMgt 1 }

ftthUmcPortTable OBJECT-TYPE
       SYNTAX      SEQUENCE OF FtthUmcPortEntry
       MAX-ACCESS  not-accessible
       STATUS      current
       DESCRIPTION "The Umc Status in FTTH system table."
       ::= { ftthUtpMgt 1}

ftthUmcPortEntry OBJECT-TYPE
       SYNTAX      FtthUmcPortEntry
       MAX-ACCESS  not-accessible
       STATUS      current
       DESCRIPTION "A conceptual row of the ftthUmcPortTable."
       INDEX  { ftthUmcPortIfIndex }
       ::= { ftthUmcPortTable 1 }

FtthUmcPortEntry ::= SEQUENCE
{
    ftthUmcPortIfIndex     Integer32,
    ftthUmcPowerStatus     INTEGER,
    ftthLipFefiStatus      INTEGER,
    ftthMCFaultStatus      INTEGER,
    ftthUmcLinkStatus      INTEGER,
    ftthLoopBackStatus     INTEGER
}

ftthUmcPortIfIndex OBJECT-TYPE
       SYNTAX      Integer32
       MAX-ACCESS  not-accessible
       STATUS      current
       DESCRIPTION "This is defined as the ifIndex in IF-MIB."
       ::= { ftthUmcPortEntry 1 }

ftthUmcPowerStatus OBJECT-TYPE
      SYNTAX      INTEGER
                  {
                    powerFail(1),
                    linkDown(2),
                    linkUp(3)
                  }
      MAX-ACCESS  read-only
      STATUS      current
      DESCRIPTION "The UMC Power Status of the FTTH system. powerFail(1)
                   means remote MC power failure for the optical fiber of the
                   link up port. linkDown(2) means the optical fiber
                   port is link down and remote MC power is good. linkUp(3)
                   means the optical fiber port is link up and remote
                   MC power is good."
      ::= { ftthUmcPortEntry 2 }

ftthLipFefiStatus OBJECT-TYPE
      SYNTAX      INTEGER
                  {
                    normal(1),
                    lip(2),
                    fefi(3)
                   }
      MAX-ACCESS  read-only
      STATUS      current
      DESCRIPTION "The indication is normal(1) when in a normal state,
                  the indication is lip (2) when the remote UMC is receiving
                  low input power on the optical port, the indication is fefi(3) when
                  far end fault indication is reported by the device."
      ::= { ftthUmcPortEntry 3 }

ftthMCFaultStatus OBJECT-TYPE
      SYNTAX      INTEGER
                  {
                    normal(1),
                    fault(2)
                   }
      MAX-ACCESS  read-only
      STATUS      current
      DESCRIPTION "The media converter fault status of the FTTH system. normal(1)
                   means the remote media converter is in normal status, fault(2)
                   indicates a fault in the remote media converter."
      ::= { ftthUmcPortEntry 4 }

ftthUmcLinkStatus OBJECT-TYPE
      SYNTAX      INTEGER
                  {
                   undefined(1),
                   linkDown(2),
                   linkUp(3)
                  }
      MAX-ACCESS  read-only
      STATUS      current
      DESCRIPTION "The indication is undefined(1) when the remote UTP port status
                   is unknown, the indication is linkDown(2) when the remote media
                   converter UTP port is link down, the indication is linkUp(3)
                   when the remote media converter UTP port is link up."
      ::= { ftthUmcPortEntry 5 }

ftthLoopBackStatus OBJECT-TYPE
      SYNTAX     INTEGER
                 {
                    stop(1),
                    start(2)
                 }
      MAX-ACCESS  read-only
      STATUS      current
      DESCRIPTION "The loop back status of the FTTH system."
      ::= { ftthUmcPortEntry 6 }

ftthUtpPortTable OBJECT-TYPE
       SYNTAX      SEQUENCE OF FtthUtpPortEntry
       MAX-ACCESS  not-accessible
       STATUS      current
       DESCRIPTION "The UTP Port Status table in FTTH system."
       ::= { ftthUtpMgt 2 }

ftthUtpPortEntry OBJECT-TYPE
       SYNTAX      FtthUtpPortEntry
       MAX-ACCESS  not-accessible
       STATUS      current
       DESCRIPTION "A conceptual row of the ftthUtpPortTable."
       INDEX  { ftthUtpPortIfIndex }
       ::= { ftthUtpPortTable 1 }

FtthUtpPortEntry ::= SEQUENCE
{
    ftthUtpPortIfIndex         Integer32,
    ftthUtpPortLinkSpeed       INTEGER,
    ftthUtpPortDuplexMode      INTEGER,
    ftthUtpPortLinkNegotiation INTEGER
}

ftthUtpPortIfIndex OBJECT-TYPE
       SYNTAX      Integer32
       MAX-ACCESS  not-accessible
       STATUS      current
       DESCRIPTION "This is defined as the ifIndex in IF-MIB."
       ::= { ftthUtpPortEntry 1 }

ftthUtpPortLinkSpeed OBJECT-TYPE
       SYNTAX      INTEGER
                   {
                     undefined(1),
                     others(2),
                     tenBase(3),
                     hundredBase(4),
                     gigaBase(5)
                   }
       MAX-ACCESS  read-only
       STATUS      current
       DESCRIPTION "The UTP port link speed of the UTP port."
       ::= { ftthUtpPortEntry 2 }

ftthUtpPortDuplexMode OBJECT-TYPE
       SYNTAX      INTEGER
                   {
                     undefined(1),
                     halfDuplex(2),
                     fullDuplex(3)
                   }
       MAX-ACCESS  read-only
       STATUS      current
       DESCRIPTION "The UTP Port Duplex mode of the UTP port."
       ::= { ftthUtpPortEntry 3 }

ftthUtpPortLinkNegotiation OBJECT-TYPE
       SYNTAX      INTEGER
                   {
                     undefined(1),
                     available(2),
                     unavailable(3)
                   }
       MAX-ACCESS  read-only
       STATUS      current
       DESCRIPTION "UTP port link negotiation."
       ::= { ftthUtpPortEntry 4 }

ftthVendorPortTable OBJECT-TYPE
       SYNTAX      SEQUENCE OF FtthVendorPortEntry
       MAX-ACCESS  not-accessible
       STATUS      current
       DESCRIPTION "The vendor information table in FTTH system."
       ::= { ftthUtpMgt 3 }

ftthVendorPortEntry OBJECT-TYPE
       SYNTAX      FtthVendorPortEntry
       MAX-ACCESS  not-accessible
       STATUS      current
       DESCRIPTION "A conceptual row of the ftthVendorPortTable."
       INDEX  { ftthVendorPortIfIndex }
       ::= { ftthVendorPortTable 1 }

FtthVendorPortEntry ::= SEQUENCE
{
    ftthVendorPortIfIndex        Integer32,
    ftthVendorCode               OCTET STRING,
    ftthVendorModelNumber        OCTET STRING,
    ftthVendorCpeVersion         Integer32,
    ftthVendorCpeInterfaceNumber INTEGER
}

ftthVendorPortIfIndex OBJECT-TYPE
       SYNTAX      Integer32
       MAX-ACCESS  not-accessible
       STATUS      current
       DESCRIPTION "This is defined as the ifIndex in IF-MIB."
       ::= { ftthVendorPortEntry 1 }

ftthVendorCode OBJECT-TYPE
       SYNTAX      OCTET STRING(SIZE(0..20))
       MAX-ACCESS  read-only
       STATUS      current
       DESCRIPTION "The FTTH System vendor code."
       ::= { ftthVendorPortEntry 2 }


ftthVendorModelNumber OBJECT-TYPE
       SYNTAX      OCTET STRING(SIZE(0..20))
       MAX-ACCESS  read-only
       STATUS      current
       DESCRIPTION "The FTTH System vendor model number."
       ::= { ftthVendorPortEntry 3 }

ftthVendorCpeVersion OBJECT-TYPE
       SYNTAX      Integer32
       MAX-ACCESS  read-only
       STATUS      current
       DESCRIPTION "The CPE version of the FTTH system."
       ::= { ftthVendorPortEntry 4 }

ftthVendorCpeInterfaceNumber OBJECT-TYPE
       SYNTAX      INTEGER
                   {
                      single(1),
                      multiple(2)
                   }
       MAX-ACCESS  read-only
       STATUS      current
       DESCRIPTION "The CPE Interface Number."
       ::= { ftthVendorPortEntry 5 }


ftthEnableIndividualTrapMgt       OBJECT IDENTIFIER ::= { ftthMgt 2 }
ftthEnableNormalTrapMgt           OBJECT IDENTIFIER ::= { ftthEnableIndividualTrapMgt 1 }
ftthEnableFaultTrapMgt            OBJECT IDENTIFIER ::= { ftthEnableIndividualTrapMgt 2 }
ftthEnableAlarmSensivitityTrapMgt OBJECT IDENTIFIER ::= { ftthEnableIndividualTrapMgt 3 }

ftthTrapEnableInterfaceCardColdStart OBJECT-TYPE
    SYNTAX     EnabledStatus
    MAX-ACCESS read-write
    STATUS     current
    DESCRIPTION "Whether the Interface Card Cold Start trap is enabled."
    ::= { ftthEnableNormalTrapMgt 1 }

ftthTrapEnableUmcPowerDown OBJECT-TYPE
    SYNTAX     EnabledStatus
    MAX-ACCESS read-write
    STATUS     current
    DESCRIPTION "Whether the UMC Power Down trap is enabled."
    ::= { ftthEnableNormalTrapMgt 2 }

ftthTrapEnableUmcPowerUp OBJECT-TYPE
    SYNTAX     EnabledStatus
    MAX-ACCESS read-write
    STATUS     current
    DESCRIPTION "Whether the UMC Power Up trap is enabled."
    ::= { ftthEnableNormalTrapMgt 3 }

ftthTrapEnableLoopBackTestStart OBJECT-TYPE
    SYNTAX     EnabledStatus
    MAX-ACCESS read-write
    STATUS     current
    DESCRIPTION "Whether the Loop Back Test Start trap is enabled."
    ::= { ftthEnableNormalTrapMgt 4 }

ftthTrapEnableLoopBackNotTest OBJECT-TYPE
    SYNTAX     EnabledStatus
    MAX-ACCESS read-write
    STATUS     current
    DESCRIPTION "Whether the Loop Back Not Test trap is enabled."
    ::= { ftthEnableNormalTrapMgt 5 }

ftthTrapEnableLoopBackOAMSettingTimeout OBJECT-TYPE
    SYNTAX     EnabledStatus
    MAX-ACCESS read-write
    STATUS     current
    DESCRIPTION "Whether the Loop Back OAM Setting Timeout trap is enabled."
    ::= { ftthEnableNormalTrapMgt 6 }

ftthTrapEnableLoopBackLBErrorTimeout OBJECT-TYPE
    SYNTAX     EnabledStatus
    MAX-ACCESS read-write
    STATUS     current
    DESCRIPTION "Whether the LoopBackLBErrorTimeout trap is enabled."
    ::= { ftthEnableNormalTrapMgt 7 }

ftthTrapEnableLoopBackOAMReleaseTimeout OBJECT-TYPE
    SYNTAX     EnabledStatus
    MAX-ACCESS read-write
    STATUS     current
    DESCRIPTION "Whether the Loop Back OAM Release Timeout trap is enabled."
    ::= { ftthEnableNormalTrapMgt 8 }

ftthTrapEnableLoopBackNormalEnd OBJECT-TYPE
    SYNTAX     EnabledStatus
    MAX-ACCESS read-write
    STATUS     current
    DESCRIPTION "Whether the Loop Back Normal End trap is enabled."
    ::= { ftthEnableNormalTrapMgt 9 }

ftthTrapEnableLoopBackBusy OBJECT-TYPE
    SYNTAX     EnabledStatus
    MAX-ACCESS read-write
    STATUS     current
    DESCRIPTION "Whether the Loop Back Busy trap is enabled."
    ::= { ftthEnableNormalTrapMgt 10 }

ftthTrapEnableLoopBackStop OBJECT-TYPE
    SYNTAX     EnabledStatus
    MAX-ACCESS read-write
    STATUS     current
    DESCRIPTION "Whether the Loop Back Stop trap is enabled."
    ::= { ftthEnableNormalTrapMgt 11 }

ftthTrapEnableLoopBackUMCTimeout OBJECT-TYPE
    SYNTAX     EnabledStatus
    MAX-ACCESS read-write
    STATUS     current
    DESCRIPTION "Whether the Loop Back UMC Timeout trap is enabled."
    ::= { ftthEnableNormalTrapMgt 12 }

ftthTrapEnableDiagnosisStart OBJECT-TYPE
    SYNTAX     EnabledStatus
    MAX-ACCESS read-write
    STATUS     current
    DESCRIPTION "Whether the Diagnosis Start trap is enabled."
    ::= { ftthEnableNormalTrapMgt 13 }

ftthTrapEnableDiagonsisResult OBJECT-TYPE
    SYNTAX     EnabledStatus
    MAX-ACCESS read-write
    STATUS     current
    DESCRIPTION "Whether the Diagonsis Result trap is enabled."
    ::= { ftthEnableNormalTrapMgt 14 }

ftthTrapEnableFanFailure OBJECT-TYPE
    SYNTAX     EnabledStatus
    MAX-ACCESS read-write
    STATUS     current
    DESCRIPTION "Whether the Fan Failure trap is enabled."
    ::= { ftthEnableFaultTrapMgt 1 }

ftthTrapEnableFanRecover OBJECT-TYPE
    SYNTAX     EnabledStatus
    MAX-ACCESS read-write
    STATUS     current
    DESCRIPTION "Whether the Fan Recover trap is enabled."
    ::= { ftthEnableFaultTrapMgt 2 }

ftthTrapEnableUmcLip OBJECT-TYPE
    SYNTAX     EnabledStatus
    MAX-ACCESS read-write
    STATUS     current
    DESCRIPTION "Whether the UMC Lip trap is enabled."
    ::= { ftthEnableFaultTrapMgt 3 }

ftthTrapEnableUmcLipRecover OBJECT-TYPE
    SYNTAX     EnabledStatus
    MAX-ACCESS read-write
    STATUS     current
    DESCRIPTION "Whether the UMC Lip Recover trap is enabled."
    ::= { ftthEnableFaultTrapMgt 4 }

ftthTrapEnableUmcLinkDown OBJECT-TYPE
    SYNTAX     EnabledStatus
    MAX-ACCESS read-write
    STATUS     current
    DESCRIPTION "Whether the UMC Link Down trap is enabled."
    ::= { ftthEnableFaultTrapMgt 5 }

ftthTrapEnableUmcLinkUp OBJECT-TYPE
    SYNTAX     EnabledStatus
    MAX-ACCESS read-write
    STATUS     current
    DESCRIPTION "Whether the UMC Link Up trap is enabled."
    ::= { ftthEnableFaultTrapMgt 6 }

ftthTrapEnableUmcMCFault OBJECT-TYPE
    SYNTAX     EnabledStatus
    MAX-ACCESS read-write
    STATUS     current
    DESCRIPTION "Whether the UMC MC Fault trap is enabled."
    ::= { ftthEnableFaultTrapMgt 7 }

ftthTrapEnableUmcMCFaultRecover OBJECT-TYPE
    SYNTAX     EnabledStatus
    MAX-ACCESS read-write
    STATUS     current
    DESCRIPTION "Whether the UMC MC Fault Recover trap is enabled."
    ::= { ftthEnableFaultTrapMgt 8 }

ftthTrapEnableLinkDown OBJECT-TYPE
    SYNTAX     EnabledStatus
    MAX-ACCESS read-write
    STATUS     current
    DESCRIPTION "Whether the Link Down trap is enabled. Note, this is
                  different from Rfc1215 (LinkDown) trap. Here we
                  should bind the variables of slot# + Port#."
    ::= { ftthEnableFaultTrapMgt 9 }

ftthTrapEnableLinkUp OBJECT-TYPE
    SYNTAX     EnabledStatus
    MAX-ACCESS read-write
    STATUS     current
    DESCRIPTION "Whether the Link Up trap is enabled. Note, this is
                  different from Rfc1215 (LinkUp) trap. Here we
                  should bind the variables of slot# + Port#."
    ::= { ftthEnableFaultTrapMgt 10 }

ftthTrapEnableHardwareFault OBJECT-TYPE
    SYNTAX     EnabledStatus
    MAX-ACCESS read-write
    STATUS     current
    DESCRIPTION "Whether the Hardware Fault trap is enabled."
    ::= { ftthEnableFaultTrapMgt 11 }

ftthTrapEnableHardwareFaultRecover OBJECT-TYPE
    SYNTAX     EnabledStatus
    MAX-ACCESS read-write
    STATUS     current
    DESCRIPTION "Whether the HardwareFaultRecover trap is enabled."
    ::= { ftthEnableFaultTrapMgt 12 }

ftthTrapEnableLinkChangeEvent OBJECT-TYPE
    SYNTAX     EnabledStatus
    MAX-ACCESS read-write
    STATUS     current
    DESCRIPTION "Whether the Link Change Event trap is enabled."
    ::= { ftthEnableAlarmSensivitityTrapMgt 1 }

ftthTrapEnableUmcUtpLinkEvent OBJECT-TYPE
    SYNTAX     EnabledStatus
    MAX-ACCESS read-write
    STATUS     current
    DESCRIPTION "Whether the UMC UTP Link Event trap is enabled."
    ::= { ftthEnableAlarmSensivitityTrapMgt 2 }

ftthTrapEnableUmcLipEvent OBJECT-TYPE
    SYNTAX     EnabledStatus
    MAX-ACCESS read-write
    STATUS     current
    DESCRIPTION "Whether the UMC Lip Event trap is enabled."
    ::= { ftthEnableAlarmSensivitityTrapMgt 3 }

ftthTrapEnableUmcMCFaultEvent OBJECT-TYPE
    SYNTAX     EnabledStatus
    MAX-ACCESS read-write
    STATUS     current
    DESCRIPTION "Whether the UMC MC Fault Event trap is enabled."
    ::= { ftthEnableAlarmSensivitityTrapMgt 4 }

ftthTrapEnableFanEvent OBJECT-TYPE
    SYNTAX     EnabledStatus
    MAX-ACCESS read-write
    STATUS     current
    DESCRIPTION "Whether the Fan Event trap is enabled."
    ::= { ftthEnableAlarmSensivitityTrapMgt 5 }

ftthTrapEnableHardwareFaultEvent OBJECT-TYPE
    SYNTAX     EnabledStatus
    MAX-ACCESS read-write
    STATUS     current
    DESCRIPTION "Whether the HardwareFaultEvent trap is enabled."
    ::= { ftthEnableAlarmSensivitityTrapMgt 6 }

ftthSysMgt OBJECT IDENTIFIER ::= { ftthMgt 3 }

ftthSysTTCMaintenance OBJECT-TYPE
    SYNTAX     EnabledStatus
    MAX-ACCESS read-write
    STATUS     current
    DESCRIPTION "Set enabled(1) to enable the TTC maintenance frame system. Set
                 disabled(2) to disable the TTC mainttenance frame system."
    ::= { ftthSysMgt 1 }


--
-- sysTimeMgt
--

sntpMgt OBJECT IDENTIFIER ::= { sysTimeMgt 1 }

sntpStatus OBJECT-TYPE
    SYNTAX      EnabledStatus
    MAX-ACCESS  read-write
    STATUS      current
    DESCRIPTION "Set enabled(1) to enable the SNTP, set disabled(2) to disable
                 the SNTP."
    ::= { sntpMgt 1 }

sntpServiceMode OBJECT-TYPE
    SYNTAX      INTEGER
                {
                    unicast(1),
                    broadcast(2),
                    anycast(3)
                }
    MAX-ACCESS  read-write
    STATUS      current
    DESCRIPTION "Service mode."
    ::= { sntpMgt 2 }

sntpPollInterval OBJECT-TYPE
    SYNTAX      Integer32(16..16384)
    MAX-ACCESS  read-write
    STATUS      current
    DESCRIPTION "Polling interval."
    ::= { sntpMgt 3 }

sntpServerTable OBJECT-TYPE
        SYNTAX      SEQUENCE OF SntpServerEntry
        MAX-ACCESS  not-accessible
        STATUS      current
        DESCRIPTION "Table for SNTP servers"
        ::= { sntpMgt 4 }

sntpServerEntry OBJECT-TYPE
        SYNTAX      SntpServerEntry
        MAX-ACCESS  not-accessible
        STATUS      current
        DESCRIPTION "Entry for SNTP servers."
        INDEX       { sntpServerIndex }
        ::= { sntpServerTable 1 }

SntpServerEntry ::= SEQUENCE
{
    sntpServerIndex Integer32,
    sntpServerIpAddress IpAddress,
    sntpServerHostName DisplayString
}


sntpServerIndex OBJECT-TYPE
    SYNTAX      Integer32 (1..3)
    MAX-ACCESS  not-accessible
    STATUS      current
    DESCRIPTION "The index of a server. This table has fixed size."
    ::= { sntpServerEntry 1 }

sntpServerIpAddress OBJECT-TYPE
    SYNTAX      IpAddress
    MAX-ACCESS  read-write
    STATUS      current
    DESCRIPTION "The IP address of a server. Valid IP addresses
                 must occupy contiguous indexes.
                 All IP addresses after the last valid index are 0."
    ::= { sntpServerEntry 2 }

sntpServerHostName OBJECT-TYPE
    SYNTAX      DisplayString(SIZE(0..255))
    MAX-ACCESS  read-write
    STATUS      current
    DESCRIPTION "If DNS client is supported, both host names and IP addresses
                are stored in 'sntpServerHostName' as contiguous indexes.
                All servers after the last valid index is an empty string ('').
                For non-IP-address entries, the correspending sntpServerIpAddress
                contains 0.0.0.0."
    ::= { sntpServerEntry 3 }

sysCurrentTime OBJECT-TYPE
     SYNTAX      DisplayString(SIZE(20))
     MAX-ACCESS  read-write
     STATUS      current
     DESCRIPTION "This is a text string in the following form, based on Unix:
                  'Mmm _d hh:mm:ss yyyy'. 'Mmm' are the first three letters
                  of the English name of the month. '_d' is the day of month.
                  A single-digit day is preceded by a space. 'hh:mm:ss' is
                  a 24-hour representations of hours, minutes, and seconds.
                  A single-digit hour is preceded by a zero. 'yyyy' is a
                  four-digit year. An example is: 'Jan  1 02:03:04 2002'."
     ::= { sysTimeMgt 2 }

sysTimeZone OBJECT-TYPE
     SYNTAX      DisplayString(SIZE(6))
     MAX-ACCESS  read-write
     STATUS      current
     DESCRIPTION "This is a text string in the following form: '[s]hh:mm'.
                  '[s]' is a plus-or-minus sign. For UTC, this is omitted.
                  For a positive offset, this is '+'. For a negative offset,
                  this is '-'. 'hh:mm' in the hour and minute offset from UTC.
                  A single-digit hour is preceded by a zero."
     ::= { sysTimeMgt 3 }

sysTimeZoneName OBJECT-TYPE
     SYNTAX      DisplayString(SIZE(1..30))
     MAX-ACCESS  read-write
     STATUS      current
     DESCRIPTION "The name of the time zone."
     ::= { sysTimeMgt 4 }

ntpMgt OBJECT IDENTIFIER ::= { sysTimeMgt 5}

ntpStatus OBJECT-TYPE
            SYNTAX      EnabledStatus
            MAX-ACCESS  read-write
            STATUS      current
            DESCRIPTION "Set enabled(1) to enable the NTP, set disabled(2) to disable
                     the NTP."
	::= { ntpMgt 1 }

ntpServiceMode OBJECT-TYPE
    	SYNTAX      INTEGER
                {
                    unicast(1)
                }
    	MAX-ACCESS  read-write
    	STATUS      current
    	DESCRIPTION "Service mode."
	::= { ntpMgt 2 }

ntpPollInterval OBJECT-TYPE
    	SYNTAX      Integer32(16..16384)
    	MAX-ACCESS  read-write
    	STATUS      current
    	DESCRIPTION "Polling interval."
    	::= { ntpMgt 3 }

ntpAuthenticateStatus OBJECT-TYPE
            SYNTAX      EnabledStatus
            MAX-ACCESS  read-write
            STATUS      current
            DESCRIPTION "Set enabled(1) to enable the NTP Authenticate, set disabled(2) to
                     disable  the NTP."
	::= { ntpMgt 4 }

ntpServerTable OBJECT-TYPE
        	SYNTAX      SEQUENCE OF NtpServerEntry
        	MAX-ACCESS  not-accessible
        	STATUS      current
        	DESCRIPTION "Table for NTP servers"
        	::= { ntpMgt 5 }

ntpServerEntry OBJECT-TYPE
        	SYNTAX      NtpServerEntry
        	MAX-ACCESS  not-accessible
        	STATUS      current
        	DESCRIPTION "Entry for NTP servers."
        	INDEX       { ntpServerIpAddress }
        	::= { ntpServerTable 1 }

NtpServerEntry ::= SEQUENCE
	{
	ntpServerIpAddress IpAddress,
	ntpServerVersion Integer32,
	ntpServerKeyId       Integer32,
	ntpServerStatus INTEGER
	}

ntpServerIpAddress OBJECT-TYPE
    	SYNTAX      IpAddress
    	MAX-ACCESS  not-accessible
    	STATUS      current
    	DESCRIPTION "The IP address of a server. Valid IP addresses
                 must occupy contiguous indexes.
                 All IP addresses after the last valid index is 0."
    	::= { ntpServerEntry 1 }

ntpServerVersion OBJECT-TYPE
        	SYNTAX      Integer32 (1..3)
        	MAX-ACCESS  read-create
        	STATUS      current
        	DESCRIPTION "NTP version."
        	::= { ntpServerEntry 2 }

ntpServerKeyId       OBJECT-TYPE
        SYNTAX      Integer32 (1..65535)
        MAX-ACCESS  read-write
        STATUS      current
        DESCRIPTION "Key for a NTP server.  This variable can only be written."
           ::= { ntpServerEntry 3 }

ntpServerStatus OBJECT-TYPE
        SYNTAX     INTEGER
               {
                   create(1),
                   active(2),
                   destroy(3)
               }
        MAX-ACCESS  read-create
        STATUS      current
        DESCRIPTION "The status of this conceptual row entry. This object isused to manage the
                     creation and deletion of conceptual rows.

                     The status column has six defined values:

		     	     - 'active', which indicates that the conceptual row is
		             available for use by the managed device;

			     - 'create', which is supplied by a management
			     station wishing to create a new instance of a
			     conceptual row and to have its status automatically set
			     to active, making it available for use by the managed
			     device;

			     - 'destroy', which is supplied by a management station
			     wishing to delete all of the instances associated with
			     an existing conceptual row."
        ::= { ntpServerEntry 4 }

ntpAuthKeyTable OBJECT-TYPE
        	SYNTAX      SEQUENCE OF NtpAuthKeyEntry
        	MAX-ACCESS  not-accessible
        	STATUS      current
        	DESCRIPTION "Table for NTP Authentication keys"
        	::= { ntpMgt 6 }

ntpAuthKeyEntry OBJECT-TYPE
        	SYNTAX      NtpAuthKeyEntry
        	MAX-ACCESS  not-accessible
        	STATUS      current
        	DESCRIPTION "Entry for NTP Authentication keys."
        	INDEX       { ntpAuthKeyId }
        	::= { ntpAuthKeyTable 1 }

NtpAuthKeyEntry::= SEQUENCE
	{
	ntpAuthKeyId Integer32,
	ntpAuthKeyWord OCTET STRING,
	ntpAuthKeyStatus INTEGER
	}

ntpAuthKeyId OBJECT-TYPE
    	SYNTAX      Integer32 (1..65536)
    	MAX-ACCESS  not-accessible
    	STATUS      current
    	DESCRIPTION "The index of a Authentication key. This table has fixed size."
    	::= { ntpAuthKeyEntry 1 }

ntpAuthKeyWord OBJECT-TYPE
    	SYNTAX      OCTET STRING (SIZE (1..32))
    	MAX-ACCESS  read-create
    	STATUS      current
    	DESCRIPTION "The Authentication key word is used to created a key  by the MD5
	And the max length is 32."
    	::= { ntpAuthKeyEntry 2 }

ntpAuthKeyStatus OBJECT-TYPE
        SYNTAX          INTEGER
               {
                   create(1),
                   active(2),
                   destroy(3)
               }
        MAX-ACCESS  read-create
        STATUS      current
	DESCRIPTION "The status of this conceptual row entry. This object isused to manage the
                     creation and deletion of conceptual rows.

                     The status column has six defined values:

			     - 'active', which indicates that the conceptual row is
			     available for use by the managed device;

			     - 'create', which is supplied by a management
			     station wishing to create a new instance of a
			     conceptual row and to have its status automatically set
			     to active, making it available for use by the managed
			     device;

			     - 'destroy', which is supplied by a management station
			     wishing to delete all of the instances associated with
			     an existing conceptual row."
        ::= { ntpAuthKeyEntry 3 }

--
-- fileMgt
--

-- Management for File System Manipulate, including files copy, display and delete.


fileCopyMgt OBJECT IDENTIFIER ::= { fileMgt 1 }
--
-- This performs the copy operation.
--

fileCopySrcOperType OBJECT-TYPE
    SYNTAX     INTEGER
               {
                 file(1),
                 runningCfg(2),
                 startUpCfg(3),
                 tftp(4),
                 unit(5),
                 http(6)
                }
    MAX-ACCESS read-write
    STATUS     current

    DESCRIPTION "The Copy Operation that we want to perform on the
                 fileCopyDestOperType, this operation is similar to the CLI
                 command 'copy fileCopySrcOperType fileCopyDestOperType'.

                 file(1) means we want to perform the 'copy file fileCopyDestType'
                 operation. runningCfg(2) means we want to perform the
                 'copy running-config fileCopyDestOperType' operation.
                 startUpCfg(3) means we want to perform the
                 'copy startup-config fileCopyDestOperType' operation. tftp(4) means
                 we want to perform the 'copy tftp fileCopyDestOperType' operation.
                 unit(5) is only available in stacking systems, in which we
                 can copy files from one unit to another unit and it means
                 we want to perform the 'copy unit fileCopyDestOperType' operation.
                 http(6) means we can read the status of the transfer via
                 HTTP protocol, but can not change the status.

                 The possible permutations are as follows: (1)copy file file
                 (2)copy file runningCfg (3) copy file startUpCfg
                 (4)copy file tftp (5) copy file unit(for stacking systems only)
                 (6)copy runningCfg file (7)copy runningCfg startUpCfg
                 (8)copy runningCfg tftp (9)copy startupCfg file
                 (10)copy startupCfg runningCfg (11)copy startupCfg tftp
                 (12)copy tftp file (13)copy tftp runningCfg
                 (14)copy tftp startUpCfg (15)copy unit file."

    ::= { fileCopyMgt 1}

fileCopySrcFileName OBJECT-TYPE
    SYNTAX     DisplayString (SIZE(0..127))
    MAX-ACCESS read-write
    STATUS     current
    DESCRIPTION
        "The source file name for fileCopyMgt when a copy
        operation is next requested via this MIB. This value is set to
        a zero length string when no file name has been specified.
        Note: If the fileCopySrcOperType is runningCfg(2) or startUpCfg(3),
        this variable can be ignored."
    ::= { fileCopyMgt 2 }

fileCopyDestOperType OBJECT-TYPE
    SYNTAX     INTEGER
               {
                 file(1),
                 runningCfg(2),
                 startUpCfg(3),
                 tftp(4),
                 unit(5),
                 http(6)
                }
    MAX-ACCESS read-write
    STATUS     current

    DESCRIPTION "The Copy Operation that we want to perform on
                 fileCopySrcOperType, this operation is similar to the CLI
                 command 'copy fileCopySrcOperType fileCopyDestOperType'.

                 file(1) means we want to perform the 'copy fileCopySrcType file '
                 operation. runningCfg(2) means we want to perform the
                 'copy fileCopySrcOperType running-config' operation.
                 startUpCfg(3) means we want to perform the
                 'copy fileCopySrcOperType startup-config' operation. tftp(4) means
                 we want to perform the 'copy fileCopySrcOperType tftp' operation,
                 unit(5) is only available in stacking systems in which we
                 can copy files from one unit to another unit. It means
                 we want to perform the 'copy fileCopySrcOperType unit' operation.
                 http(6) means we can read the status of the transfer via
                 HTTP protocol, but can not change the status.

                 The possible permutations are as follows: (1)copy file file
                 (2)copy file runningCfg (3) copy file startUpCfg
                 (4)copy file tftp (5) copy file unit(for stacking system only)
                 (6)copy runningCfg file (7)copy runningCfg startUpCfg
                 (8)copy runningCfg tftp (9)copy startupCfg file
                 (10)copy startupCfg runningCfg (11)copy startupCfg tftp
                 (12)copy tftp file (13)copy tftp runningCfg
                 (14)copy tftp startUpCfg (15)copy unit file."

    ::= { fileCopyMgt 3 }

fileCopyDestFileName  OBJECT-TYPE
    SYNTAX     DisplayString (SIZE(0..127))
    MAX-ACCESS read-write
    STATUS     current
    DESCRIPTION
        "The destination file name for fileCopyMgt when a
        copy operation is next requested via this MIB.  This value is set to
        a zero length string when no file name has been specified.
        Note: If the fileCopyDestOperType is runningCfg(2) or startupCfg(3),
        this variable can be ignored."
    ::= { fileCopyMgt 4 }

fileCopyFileType  OBJECT-TYPE
    SYNTAX     INTEGER {
                  opcode(1),
                  config(2),
                  bootRom(3),
                  controller(4)
               }
    MAX-ACCESS read-write
    STATUS     current
    DESCRIPTION
        "Type of file to copy in fileCopyMgt. If the fileCopySrcOperType or
         fileCopyDestOperType is either runningCfg(2) or startupCfg(3), this
         variable can be ignored. If the fileCopySrcOperType or fileCopyDestOperType
         is unit(5), this variable cannot be set to bootRom(3)."
    ::= { fileCopyMgt 5 }

fileCopyTftpServer  OBJECT-TYPE
    SYNTAX     IpAddress
    MAX-ACCESS read-write
    STATUS     current
    DESCRIPTION
        "The IP address of the TFTP server for transfer
        when a download is next requested via this MIB.
        This value is set to '0.0.0.0' when no IP address has been
        specified. If neither fileCopySrcOperType nor fileCopyDestOperType
        is tftp(4), this variable can be ignored."
    ::= { fileCopyMgt 6 }

fileCopyUnitId OBJECT-TYPE
    SYNTAX      Integer32
    MAX-ACCESS  read-write
    STATUS      current
    DESCRIPTION "Specifies the switch unit for stackable devices.
                When performing the 'copy unit file' or 'copy file unit' action,
                if neither fileCopySrcOperType nor fileCopyDestOperType
                is unit(5), this variable can be ignored."
    ::= { fileCopyMgt 7 }

fileCopyAction OBJECT-TYPE
    SYNTAX      INTEGER
                {
                  notCopying(1),
                  copy(2),
                  abortTftp(3)
                }
    MAX-ACCESS read-write
    STATUS     current
    DESCRIPTION
          "Setting this object to copy(2) to begin the copy Operation.
           Setting this object to abortTftp(3) to abort a TFTP transfer."
    ::= { fileCopyMgt 8 }


fileCopyStatus  OBJECT-TYPE
    SYNTAX     FileCopyStatus
    MAX-ACCESS read-only
    STATUS     current
    DESCRIPTION
        "The status of the last copy procedure, if any. This
        object will have a value of fileCopyUnknown(18) if no
        copy operation has been performed."
    ::= { fileCopyMgt 9 }

fileCopyTftpErrMsg OBJECT-TYPE
    SYNTAX      DisplayString(SIZE(0..255))
    MAX-ACCESS read-only
    STATUS     current
    DESCRIPTION
          "TFTP error message, this value is meaningful only when the fileCopyStatus is
          fileCopyTftpUndefError(1)."
    ::= { fileCopyMgt 10 }

fileCopyTftpServerHostName  OBJECT-TYPE
    SYNTAX     DisplayString(SIZE(0..255))
    MAX-ACCESS read-write
    STATUS     current
    DESCRIPTION
        "The IP address or DNS of the TFTP server for transfer
        when a download is next requested via this MIB.
        This value is set to '0.0.0.0' when no IP address has been
        specified. If neither fileCopySrcOperType nor fileCopyDestOperType
        is tftp(4), this variable can be ignored."
    ::= { fileCopyMgt 11 }

fileInfoMgt OBJECT IDENTIFIER ::= { fileMgt 2 }
--
-- This mangement performs the display and delete operation.
--


fileInfoTable OBJECT-TYPE
    SYNTAX       SEQUENCE OF FileInfoEntry
    MAX-ACCESS   not-accessible
    STATUS       current
    DESCRIPTION "This table contain the information of the file system;
                 we can also perform the delete, set startup file operation."

    ::= { fileInfoMgt 1 }

fileInfoEntry OBJECT-TYPE
    SYNTAX       FileInfoEntry
    MAX-ACCESS   not-accessible
    STATUS       current
    DESCRIPTION "A conceptually row for fileInfoTable."
    INDEX       {fileInfoUnitID, IMPLIED fileInfoFileName}
    ::= { fileInfoTable 1 }

FileInfoEntry ::= SEQUENCE
    {
        fileInfoUnitID                  Integer32,
        fileInfoFileName                DisplayString,
        fileInfoFileType                INTEGER,
        fileInfoIsStartUp               TruthValue,
        fileInfoFileSize                Integer32,
        fileInfoCreationTime            DisplayString,
        fileInfoDelete                  INTEGER,
        fileInfoComment                 OCTET STRING
    }

fileInfoUnitID OBJECT-TYPE
    SYNTAX       Integer32
    MAX-ACCESS   not-accessible
    STATUS       current
    DESCRIPTION "The switch unit in a stacking system, in a
                 non-stacking system, this value is always 1."
    ::= { fileInfoEntry 1 }

fileInfoFileName OBJECT-TYPE
    SYNTAX       DisplayString (SIZE (1..32))
    MAX-ACCESS   not-accessible
    STATUS       current
    DESCRIPTION "The file Name of the file System in the device."
    ::= { fileInfoEntry 2 }

fileInfoFileType OBJECT-TYPE
    SYNTAX       INTEGER
                 {
                    kernel(0),
                    diag(1),
                    runtime(2),
                    syslog(3),
                    cmdlog(4),
                    config(5),
                    postlog(6),
                    private(7),
                    certificate(8),
                    archive(9),
                    binaryConfig(10),
                    public(11),
                    cpeFirmware(12),
                    cpeConfig(13),
                    fileMapping(14),
                    license(15),
                    nosInstaller(16)
                 }
    MAX-ACCESS   read-only
    STATUS       current
    DESCRIPTION "The file type of the file System in the device."
    ::= { fileInfoEntry 3 }

fileInfoIsStartUp OBJECT-TYPE
    SYNTAX       TruthValue
    MAX-ACCESS   read-write
    STATUS       current
    DESCRIPTION "This flag indicate whether this file is a startup file. Set this
                 object to true(1) to indicate that this is a startup file. Setting this
                 object to false(2) is a invalid operation."
    ::= { fileInfoEntry 4 }

fileInfoFileSize OBJECT-TYPE
    SYNTAX       Integer32
    UNITS        "bytes"
    MAX-ACCESS   read-only
    STATUS       current
    DESCRIPTION "The sizes (in bytes) of the file."
    ::= { fileInfoEntry 5 }

fileInfoCreationTime OBJECT-TYPE
    SYNTAX       DisplayString(SIZE(20))
    MAX-ACCESS   read-only
    STATUS       current
    DESCRIPTION "The creation time of the file, This is a text string in the
                 following form, based on Unix: 'Mmm _d hh:mm:ss yyyy'. 'Mmm'
                 are the first three letters of the English name of the month.
                 '_d' is the day of month. A single-digit day is preceded by
                 a space. 'hh:mm:ss' is a 24-hour representations of hours,
                 minutes, and seconds. A single-digit hour is preceded by a
                 zero. 'yyyy' is the four-digit year. An example is:
                 'Jan  1 02:03:04 2002'."
    ::= { fileInfoEntry 6 }

fileInfoDelete OBJECT-TYPE
    SYNTAX       INTEGER
                 {
                  noDelete(1),
                  delete(2)
                 }
    MAX-ACCESS   read-write
    STATUS       current
    DESCRIPTION "Write this object to delete(2) to delete a file, when
                 read, this always return noDelete(1)."
    ::= { fileInfoEntry 7 }

fileInfoComment OBJECT-TYPE
    SYNTAX       OCTET STRING(SIZE(32))
    MAX-ACCESS   read-only
    STATUS       current
    DESCRIPTION "This is an implementation-dependent comment of
                 32 octets."
    ::= { fileInfoEntry 8 }

--fileAutoDownloadResultTable

fileAutoDownloadResultTable OBJECT-TYPE
    SYNTAX       SEQUENCE OF FileAutoDownloadResultEntry
    MAX-ACCESS   not-accessible
    STATUS       current
    DESCRIPTION "This table contains file auto download result information."
    ::= { fileMgt 3 }

fileAutoDownloadResultEntry OBJECT-TYPE
    SYNTAX       FileAutoDownloadResultEntry
    MAX-ACCESS   not-accessible
    STATUS       current
    DESCRIPTION "A conceptual row for fileAutoDownloadResultTable."
    INDEX       {fileAutoDownloadResultUnitID}
    ::= { fileAutoDownloadResultTable 1 }

FileAutoDownloadResultEntry ::= SEQUENCE
    {
        fileAutoDownloadResultUnitID                  Integer32,
        fileAutoDownloadResultAction                  INTEGER,
        fileAutoDownloadResultStatus                  FileCopyStatus
    }

fileAutoDownloadResultUnitID OBJECT-TYPE
    SYNTAX       Integer32
    MAX-ACCESS   not-accessible
    STATUS       current
    DESCRIPTION "The switch unit in a stacking system, in a
                 non-stacking system, this value is always 1."
    ::= { fileAutoDownloadResultEntry 1 }

fileAutoDownloadResultAction OBJECT-TYPE
    SYNTAX       INTEGER
                 {
                      notCopying(1),
                      copying(2)
                 }
    MAX-ACCESS   read-only
    STATUS       current
    DESCRIPTION "The status of the auto download action.
                 value copying(2) will be obtained if the auto download action is currently processing,
                 or value notCopying(1) will be obtained if no auto download action is currently processing.

                 You can check the download result through the fileAutoDownloadResultStatus object
                 after the download action has finished.

                 Please note that this object is read-only, since the auto download action is triggered
                 automatically by the system when an image file or a config file is set as startup setting
                 through the fileInfoIsStartUp, restartOpCodeFile or restartConfigFile objects,
                 but not set by the user manually through this fileAutoDownloadResultAction object."
    ::= { fileAutoDownloadResultEntry 2 }

fileAutoDownloadResultStatus OBJECT-TYPE
    SYNTAX       FileCopyStatus
    MAX-ACCESS   read-only
    STATUS       current
    DESCRIPTION "The last auto download result status.
                value fileCopyUnknown(18) will be obtained
                if no download action has been performed before."
    ::= { fileAutoDownloadResultEntry 3 }

--
--vrrpMgt
--

vrrpClearStatisticsAction OBJECT-TYPE
    SYNTAX       INTEGER
                 {
                    clear(1),
                    noClear(2)
                 }
    MAX-ACCESS   read-write
    STATUS       current
    DESCRIPTION "This variable is used to clear the counters
                in the  vrrpStatistics group(in VRRP-MIB, standard mib rfc2787).
                Set this variable to clear(1) to perform the clear operation,
                noClear(2) will always be displayed when reading this variable."
    ::= { vrrpMgt 1 }

vrrpRouterStatsExtTable OBJECT-TYPE
    SYNTAX       SEQUENCE OF VrrpRouterStatsExtEntry
    MAX-ACCESS   not-accessible
    STATUS       current
    DESCRIPTION "This is the VrrpRouterStatsTable extension table
                (in VRRP-MIB, standard mib rfc2787)."
    ::= { vrrpMgt 2 }

vrrpRouterStatsExtEntry OBJECT-TYPE
    SYNTAX       VrrpRouterStatsExtEntry
    MAX-ACCESS   not-accessible
    STATUS       current
    DESCRIPTION "A conceptual row for vrrpRouterStatsExtTable."
    INDEX       { ifIndex, vrrpOperVrId }
    ::= { vrrpRouterStatsExtTable 1 }

VrrpRouterStatsExtEntry ::= SEQUENCE
    {
        vrrpRouterStatsExtClearAction     INTEGER
    }

vrrpRouterStatsExtClearAction OBJECT-TYPE
    SYNTAX       INTEGER
                 {
                    clear(1),
                    noClear(2)
                 }
    MAX-ACCESS   read-write
    STATUS       current
    DESCRIPTION "This variable is used to clear the counters
                in the VrrpRouterStatsTable(in VRRP-MIB, standard mib rfc2787).
                Set this variable to clear(1) to perform the clear operation,
                noClear(2) will always be obtained when reading this variable."
    ::= { vrrpRouterStatsExtEntry 1 }

vrrpOperExtTable OBJECT-TYPE
    SYNTAX       SEQUENCE OF VrrpOperExtEntry
    MAX-ACCESS   not-accessible
    STATUS       current
    DESCRIPTION "This is the extension table of the VrrpOperTable
                (in VRRP-MIB, standard mib rfc2787)."
    ::= { vrrpMgt 3 }

vrrpOperExtEntry OBJECT-TYPE
    SYNTAX       VrrpOperExtEntry
    MAX-ACCESS   not-accessible
    STATUS       current
    DESCRIPTION "A conceptual row for vrrpOperExtTable."
    INDEX       { ifIndex, vrrpOperVrId}
    ::= { vrrpOperExtTable 1 }

VrrpOperExtEntry ::= SEQUENCE
    {
        vrrpExtOperPreemptDelay     Integer32
    }

vrrpExtOperPreemptDelay OBJECT-TYPE
    SYNTAX       Integer32
    MAX-ACCESS   read-write
    STATUS       current
    DESCRIPTION "Preempt delay time(in sec).
                 this variable can be ignored if the value of vrrpOperPreemptMode is false."
    ::= { vrrpOperExtEntry 1 }
--
--dnsMgt
--

--dnsHostTable
dnsDomainLookup OBJECT-TYPE
    SYNTAX       EnabledStatus
    MAX-ACCESS   read-write
    STATUS       current
    DESCRIPTION "To enable the IP Domain Naming System (DNS)-based host name-to-address translation."
    ::= { dnsMgt 1 }

dnsDomainName OBJECT-TYPE
    SYNTAX       DisplayString(SIZE(0..255))
    MAX-ACCESS   read-write
    STATUS       current
    DESCRIPTION "To define a default domain name to complete
                unqualified host names (names without a dotted-decimal domain name)."
    ::= { dnsMgt 2 }

dnsHostTable OBJECT-TYPE
    SYNTAX       SEQUENCE OF DnsHostEntry
    MAX-ACCESS   not-accessible
    STATUS       current
    DESCRIPTION "This table is used to define static host name-to-address mapping."
    ::= { dnsMgt 3 }

dnsHostEntry OBJECT-TYPE
    SYNTAX       DnsHostEntry
    MAX-ACCESS   not-accessible
    STATUS       current
    DESCRIPTION "A conceptual row for the dnsHostTable."
    INDEX       { dnsHostName, dnsHostIp }
    ::= { dnsHostTable 1 }

DnsHostEntry ::= SEQUENCE
    {
        dnsHostName           DisplayString,
        dnsHostIp             IpAddress,
        dnsHostStatus         ValidStatus
    }

dnsHostName OBJECT-TYPE
    SYNTAX       DisplayString(SIZE(1..255))
    MAX-ACCESS   not-accessible
    STATUS       current
    DESCRIPTION "Host name."
    ::= { dnsHostEntry 1 }

dnsHostIp OBJECT-TYPE
    SYNTAX       IpAddress
    MAX-ACCESS   not-accessible
    STATUS       current
    DESCRIPTION "Host IP."
    ::= { dnsHostEntry 2 }

dnsHostStatus OBJECT-TYPE
    SYNTAX       ValidStatus
    MAX-ACCESS   read-create
    STATUS       current
    DESCRIPTION "Setting this to valid(1) creates an entry.
                 Setting this to invalid(2) destroys an entry."
    ::= { dnsHostEntry 3 }

--dnsAliasTable
dnsAliasTable OBJECT-TYPE
    SYNTAX       SEQUENCE OF DnsAliasEntry
    MAX-ACCESS   not-accessible
    STATUS       current
    DESCRIPTION "This table displays the alias of the host name."
    ::= { dnsMgt 4 }

dnsAliasEntry OBJECT-TYPE
    SYNTAX       DnsAliasEntry
    MAX-ACCESS   not-accessible
    STATUS       current
    DESCRIPTION "A conceptual row for the dnsAliasTable."
    INDEX       { dnsAliasName, dnsAliasAlias }
    ::= { dnsAliasTable 1 }

DnsAliasEntry ::= SEQUENCE
    {
        dnsAliasName           DisplayString,
        dnsAliasAlias          DisplayString
    }

dnsAliasName OBJECT-TYPE
    SYNTAX       DisplayString(SIZE(1..255))
    MAX-ACCESS   read-only
    STATUS       current
    DESCRIPTION "Host name."
    ::= { dnsAliasEntry 1 }

dnsAliasAlias OBJECT-TYPE
    SYNTAX       DisplayString(SIZE(1..255))
    MAX-ACCESS   read-only
    STATUS       current
    DESCRIPTION "Alias."
    ::= { dnsAliasEntry 2 }

--dnsDomainListEntry
dnsDomainListTable OBJECT-TYPE
    SYNTAX       SEQUENCE OF DnsDomainListEntry
    MAX-ACCESS   not-accessible
    STATUS       current
    DESCRIPTION "This table defines a list of default domain names to complete unqualified host names."
    ::= { dnsMgt 5 }

dnsDomainListEntry OBJECT-TYPE
    SYNTAX       DnsDomainListEntry
    MAX-ACCESS   not-accessible
    STATUS       current
    DESCRIPTION "A conceptual row for the dnsDomainListTable."
    INDEX       { dnsDomainListName }
    ::= { dnsDomainListTable 1 }

DnsDomainListEntry ::= SEQUENCE
    {
        dnsDomainListName           DisplayString,
        dnsDomainListStatus             ValidStatus
    }

dnsDomainListName OBJECT-TYPE
    SYNTAX       DisplayString(SIZE(1..255))
    MAX-ACCESS   not-accessible
    STATUS       current
    DESCRIPTION "Domain name."
    ::= { dnsDomainListEntry 1 }

dnsDomainListStatus OBJECT-TYPE
    SYNTAX       ValidStatus
    MAX-ACCESS   read-create
    STATUS       current
    DESCRIPTION "Setting this to valid(1) creates an entry.
                 Setting this to invalid(2) destroys an entry."
    ::= { dnsDomainListEntry 2 }

--dnsNameServerEntry
dnsNameServerTable OBJECT-TYPE
    SYNTAX       SEQUENCE OF DnsNameServerEntry
    MAX-ACCESS   not-accessible
    STATUS       current
    DESCRIPTION "To specify the address of one or more
                 name servers to use for name and address resolution.
                 This table has fixed size, will get 0.0.0.0 dnsNameServerIp
                 if this entry does not exist."
    ::= { dnsMgt 6 }

dnsNameServerEntry OBJECT-TYPE
    SYNTAX       DnsNameServerEntry
    MAX-ACCESS   not-accessible
    STATUS       current
    DESCRIPTION "A conceptual row for dnsNameServerTable."
    INDEX       { dnsNameServerIndex }
    ::= { dnsNameServerTable 1 }

DnsNameServerEntry ::= SEQUENCE
{
    dnsNameServerIndex        Integer32,
    dnsNameServerIp           IpAddress
}

dnsNameServerIndex  OBJECT-TYPE
    SYNTAX       Integer32(1..6)
    MAX-ACCESS   not-accessible
    STATUS       current
    DESCRIPTION "Index of this dnsNameServerTable,
                 representing the sequence of the dnsNameServerIp."
    ::= { dnsNameServerEntry 1 }

dnsNameServerIp OBJECT-TYPE
    SYNTAX       IpAddress
    MAX-ACCESS   read-write
    STATUS       current
    DESCRIPTION "IP address of name server."
    ::= { dnsNameServerEntry 2 }

--dnsCacheEntry
dnsCacheTable OBJECT-TYPE
    SYNTAX       SEQUENCE OF DnsCacheEntry
    MAX-ACCESS   not-accessible
    STATUS       current
    DESCRIPTION "To display the RRs in DNS cache."
    ::= { dnsMgt 7 }

dnsCacheEntry OBJECT-TYPE
    SYNTAX       DnsCacheEntry
    MAX-ACCESS   not-accessible
    STATUS       current
    DESCRIPTION "A conceptual row for the dnsCacheTable."
    INDEX       { dnsCacheIndex }
    ::= { dnsCacheTable 1 }

DnsCacheEntry ::= SEQUENCE
    {
        dnsCacheIndex           Integer32,
        dnsCacheFlag            Integer32,
        dnsCacheType            INTEGER,
        dnsCacheIp              IpAddress,
        dnsCacheTtl             Integer32,
        dnsCacheDomain          DisplayString
    }

dnsCacheIndex OBJECT-TYPE
    SYNTAX       Integer32
    MAX-ACCESS   not-accessible
    STATUS       current
    DESCRIPTION "The entry sequence number."
    ::= { dnsCacheEntry 1 }

dnsCacheFlag OBJECT-TYPE
    SYNTAX       Integer32
    MAX-ACCESS   read-only
    STATUS       current
    DESCRIPTION "Always get 4, means this record is unreliable."
    ::= { dnsCacheEntry 2 }

dnsCacheType OBJECT-TYPE
    SYNTAX       INTEGER
                 {
                    cname(1),
                    alias(2)
                 }
    MAX-ACCESS   read-only
    STATUS       current
    DESCRIPTION "Cache Type: cname(1); alias(2)."
    ::= { dnsCacheEntry 3 }

dnsCacheIp OBJECT-TYPE
    SYNTAX       IpAddress
    MAX-ACCESS   read-only
    STATUS       current
    DESCRIPTION "The DNS cache IP."
    ::= { dnsCacheEntry 4 }

dnsCacheTtl OBJECT-TYPE
    SYNTAX       Integer32(0..876000)
    MAX-ACCESS   read-only
    STATUS       current
    DESCRIPTION "The DNS cache TTL."
    ::= { dnsCacheEntry 5 }

dnsCacheDomain OBJECT-TYPE
    SYNTAX       DisplayString(SIZE(1..255))
    MAX-ACCESS   read-only
    STATUS       current
    DESCRIPTION "The DNS cache domain."
    ::= { dnsCacheEntry 6 }

--
-- ledCtrlMgt
--

ledCtrlMgtColorOnOffTime  OBJECT-TYPE
           SYNTAX       INTEGER
                        {
                            off(0),
                            redNoOnOff(1),
                            redOneTimePerSec(2),
                            redTwoTimePerSec(3),
                            redFiveTimePerSec(4),
                            greenNoOnOff(5),
                            greenOneTimePerSec(6),
                            greenTwoTimePerSec(7),
                            greenFiveTimePerSec(8)
                        }
           MAX-ACCESS  read-write
           STATUS       current
           DESCRIPTION "Indicates the control led color and on off time."
           DEFVAL       { off }
          ::= { ledCtrlMgt 1 }

--
-- poeMgt
--

   -- PSE Objects

     pethPsePortTable OBJECT-TYPE
          SYNTAX      SEQUENCE OF PethPsePortEntry
          MAX-ACCESS  not-accessible
          STATUS      current
          DESCRIPTION
              "A table of objects that display and control the power
               characteristics power Ethernet ports on a Power Source
               Entity (PSE) device. This group will be implemented in
               managed power Ethernet switches and mid-span devices."
          ::= { poeMgt 1 }

      pethPsePortEntry OBJECT-TYPE
          SYNTAX      PethPsePortEntry
          MAX-ACCESS  not-accessible
          STATUS      current
          DESCRIPTION
                  "A set of objects that display and control the power
                  characteristics of a power Ethernet PSE port."
          INDEX    { pethPsePortGroupIndex , pethPsePortIndex  }
          ::= { pethPsePortTable 1 }


      PethPsePortEntry ::= SEQUENCE {
          pethPsePortGroupIndex
             Integer32,
          pethPsePortIndex
             Integer32,
          pethPsePortAdminEnable
              INTEGER,
          pethPsePortPowerPairsControlAbility
              TruthValue,
          pethPsePortPowerPairs
              INTEGER,
          pethPsePortPowerDetectionControl
              INTEGER,
          pethPsePortDetectionStatus
              INTEGER,
          pethPsePortPowerPriority
              INTEGER,
          pethPsePortPowerMaintenanceStatus
              INTEGER,
          pethPsePortMPSAbsentCounter
                Counter32,
          pethPsePortOverCurrentCounter
                Counter32,
          pethPsePortType
              INTEGER,
          pethPsePortPowerClassifications
                INTEGER
      }

        pethPsePortGroupIndex OBJECT-TYPE
          SYNTAX      Integer32 (1..2147483647)
          MAX-ACCESS  not-accessible
          STATUS      current
          DESCRIPTION
              "This variable uniquely identifies the group
               containing the port to which a power Ethernet PSE is connected.
               Group means box in the stack, module in a rack and the value 1
               MUST be used for non-modular devices .

               pethPseMidSpanGroupCapacity is the number of Mid-Span PSE
               groups that can be contained within the Mid-Span PSE."
          ::= { pethPsePortEntry 1 }

        pethPsePortIndex OBJECT-TYPE
          SYNTAX      Integer32 (1..2147483647)
          MAX-ACCESS  not-accessible
          STATUS      current
          DESCRIPTION
              "This variable uniquely identifies the power Ethernet PSE
               port within group pethPseGroupIndex to which the
               power Ethernet PSE entry is connected."
          ::= { pethPsePortEntry 2 }


        pethPsePortAdminEnable OBJECT-TYPE
       SYNTAX INTEGER   {
                  enable(1),
                  disable(2)
         }
       MAX-ACCESS read-write
       STATUS current
       DESCRIPTION
           "Enables power supply on this port.
            Setting this object at a value enable(1) enables power
            and detection mechanism for this port.
            Setting this object at a value disable(2) disables power
            for this port."
       ::= { pethPsePortEntry 3 }

        pethPsePortPowerPairsControlAbility OBJECT-TYPE
       SYNTAX TruthValue
       MAX-ACCESS read-only
       STATUS current
       DESCRIPTION
            "Describes the capability of controlling the power pairs
            functionality to switch pins for sourcing power.
            The value true indicate that the device has the capability
            to control the power pairs"
       ::= { pethPsePortEntry 4 }

        pethPsePortPowerPairs OBJECT-TYPE
       SYNTAX INTEGER   {
                  signal(1),
                  spare(2)
        }
       MAX-ACCESS read-write
       STATUS current
       DESCRIPTION
           "Describes or controls the pairs in use. If the value of
            pethPsePortPowerPairsControl is true, this object is
            writable.
            A value of signal(1) means that the signal pairs
            only are in use.
            A value of spare(2) means that the spare pairs
            only are in use."
       ::= { pethPsePortEntry 5 }

        pethPsePortPowerDetectionControl OBJECT-TYPE
       SYNTAX INTEGER   {
                  auto(1),
                  test(2)
        }
       MAX-ACCESS read-write
       STATUS current
       DESCRIPTION
           "Controls the power detection mechanism of the port.
            Setting the value auto(1) enables the power detection
            mechanism of the port.
            Setting the value test(2) puts the port in a
            testmode: force continuous discovery without applying
            power regardless of whether PD detected."
       ::= { pethPsePortEntry 6 }


        pethPsePortDetectionStatus OBJECT-TYPE
       SYNTAX INTEGER   {
                disabled(1),
                searching(2),
                  deliveringPower(4),
                  fault(5),
                  test(7),
                  denyLowPriority(8)
        }
       MAX-ACCESS read-only
       STATUS current
       DESCRIPTION
           "Describes the operational status of the port PD detection.
            A value of disabled(1)- indicates that the PSE State diagram is in
            the state IDLE
            A value of searching(2)- indicates that the PSE State diagram is in
            the state DETECTION, CLASSIFICATION, SIGNATURE_INVALID or BACKOFF.
            A value of deliveringPower(4) - indicates that the PSE State diagram
            is in the state POWER_UP, POWER_ON or POWER_OFF.
            A value of fault(5) - indicates that the PSE State diagram is in the
            state TEST_ERROR or the state IDLE due to the variable error
            condition.
            Faults detected are vendor specific.
            A value of test(7) - indicates that the PSE State diagram is in the
            state TEST_MODE.
            A value of denyLowPriority(8) indicates that the port was
            disabled by the power management system, in order to keep
            active higher priority ports.
             "
       ::= { pethPsePortEntry 7 }

        pethPsePortPowerPriority OBJECT-TYPE
       SYNTAX INTEGER   {
                  critical(1),
                  high(2),
                  low(3)
        }
       MAX-ACCESS read-write
       STATUS current
       DESCRIPTION
           "This object controls the priority of the port from the point
            of view of a power management algorithm. The priority that
            is set by this variable could be used by a control mechanism
            that prevents over current situations by disconnecting first
            ports with lower power priority. Ports that connect devices
            critical to the operation of the network - like the E911
            telephones ports - should be set to higher priority."
       ::= { pethPsePortEntry 8 }

        pethPsePortPowerMaintenanceStatus  OBJECT-TYPE
       SYNTAX INTEGER   {
                  ok(1),
                  underCurrent(2),
                  mPSAbsent(3)
        }
       MAX-ACCESS read-only
       STATUS current
       DESCRIPTION
           "The value ok(1) indicates the Power Maintenance
            Signature is present and the overcurrent condition has not been
            detected.
            The value overCurrent (2) indicates an overcurrent condition
            has been detected.
            The value mPSAbsent(3) indicates that the Power Maintenance
            Signature is absent."


       REFERENCE   "[IEEE Draft P802.3af/D4.0, November, 2002, 30.9.1.1.8
                   aPSEPowerMaintenanceStatus]"
       ::= { pethPsePortEntry 10 }

        pethPsePortMPSAbsentCounter OBJECT-TYPE
       SYNTAX Counter32
       MAX-ACCESS read-only
       STATUS current
       DESCRIPTION
             "Counts the number of times that the
                pethPsePortPowerMaintenanceStatus attribute changes from any
                value to the value mPSAbsent(3)."
       REFERENCE   "[IEEE Draft P802.3af/D4.0, November, 2002, object 30.9.1.1.9
                     aPSEUnderCurrentCounter]"
       ::= { pethPsePortEntry 11 }

        pethPsePortOverCurrentCounter OBJECT-TYPE
       SYNTAX Counter32
       MAX-ACCESS read-only
       STATUS current
       DESCRIPTION
                "Counts the number of times that the aPSEPowerCurrentStatus
                 attribute changes from any value to the value overCurrent(2)."
       REFERENCE   "[IEEE Draft P802.3af/D4.0, November, 2002, object 30.9.1.1.1
                     aPSEOverCurrentCounter]"
       ::= { pethPsePortEntry 12 }


        pethPsePortType OBJECT-TYPE
       SYNTAX INTEGER   {
                  other(1),
                  telephone(2),
                  webcam(3),
                  wireless(4)
        }
       MAX-ACCESS read-write
       STATUS current
       DESCRIPTION
           "A manager will set the value of this variable to a value
            that indicates the type of the device that is connected
            to theport. This value can be the result of the mapping
            the address of the station connected to the port and of
            the value of the pethPdPortType of the respective PD port."
       ::= { pethPsePortEntry 13 }

       pethPsePortPowerClassifications OBJECT-TYPE
        SYNTAX INTEGER   {
                  class0(1),
                  class1(2),
                  class2(3),
                  class3(4),
                  class4(5)
        }
       MAX-ACCESS read-only
       STATUS current
       DESCRIPTION
           "Classification is a way to tag different terminals on the
           Power over LAN network according to their power consumption.
           Devices such as IP telephones, WLAN access points and others,
           will be classified according to their power requirements.

          The value is only valid while a valid PD is being detected as
          indicated by the attribute pethPsePortDetectionStatus reporting
          the value or deliveringPower(4)."
       REFERENCE   "[IEEE Draft P802.3af/D4.0, November, 2002,
                     object 30.9.1.1.7 aPSEPowerClassification]"
      ::= { pethPsePortEntry 14 }

   -- Main PSE Objects

   pethMainPseObjects       OBJECT IDENTIFIER ::= { poeMgt 3 }

   pethMainPseTable OBJECT-TYPE
          SYNTAX      SEQUENCE OF PethMainPseEntry
          MAX-ACCESS  not-accessible
          STATUS      current
          DESCRIPTION
              "A table of objects that display and control the Main power
             on a PSE  device. Example - an Ethernet switch midspan device can
               control an Ethnternet port and the Main Power supply unit's."
          ::= { pethMainPseObjects 1 }

      pethMainPseEntry OBJECT-TYPE
          SYNTAX      PethMainPseEntry
          MAX-ACCESS  not-accessible
          STATUS      current
          DESCRIPTION
               "A set of objects that display and control the Main power
                of a PSE. "
          INDEX    { pethMainPseGroupIndex }
          ::= { pethMainPseTable 1 }

      PethMainPseEntry ::= SEQUENCE {
          pethMainPseGroupIndex
              Integer32,
          pethMainPsePower
              Gauge32 ,
          pethMainPseOperStatus
              INTEGER,
          pethMainPseConsumptionPower
              Gauge32,
          pethMainPseUsageThreshold
              Integer32
      }
        pethMainPseGroupIndex OBJECT-TYPE
          SYNTAX       Integer32 (1..2147483647)
          MAX-ACCESS  not-accessible
          STATUS      current
          DESCRIPTION
              "This variable uniquely identifies the group to which
              power Ethernet PSE is connected.Group means (box in the stack,
              module in a rack) and  the value 1 MUST be  used for non-modular
              devices "
          ::= { pethMainPseEntry 1 }

        pethMainPsePower OBJECT-TYPE
          SYNTAX      Gauge32  (1..65535)
          UNITS      "Watts"
          MAX-ACCESS  read-only
          STATUS      current
          DESCRIPTION
                  "The nominal power of the PSE expressed in Watts."
          ::= { pethMainPseEntry 2 }


        pethMainPseOperStatus OBJECT-TYPE
          SYNTAX INTEGER   {
                  on(1),
                  off(2),
                  faulty(3)
             }
          MAX-ACCESS  read-only
          STATUS      current
          DESCRIPTION
                  "The operational status of the main PSE."
          ::= { pethMainPseEntry 3 }

        pethMainPseConsumptionPower OBJECT-TYPE
          SYNTAX      Gauge32
          UNITS      "Watts"
          MAX-ACCESS  read-only
          STATUS      current
          DESCRIPTION
                  "Measured usage power expressed in Watts."
          ::= { pethMainPseEntry 4 }


        pethMainPseUsageThreshold OBJECT-TYPE
          SYNTAX      Integer32  (1..99)
          UNITS      "%"
          MAX-ACCESS  read-write
          STATUS      current
          DESCRIPTION
                  "The usage threshold expressed in percents for
                   comparing the measured power and initiating
                   an alarm if the threshold is exceeded."
          ::= { pethMainPseEntry 7 }


   -- Notification  Control  Objects

   pethNotificationControl        OBJECT IDENTIFIER ::= { poeMgt 4 }

   pethNotificationControlTable OBJECT-TYPE
          SYNTAX      SEQUENCE OF PethNotificationControlEntry
          MAX-ACCESS  not-accessible
          STATUS      current
          DESCRIPTION
              "A table of objects that display and control the Notification
             on a PSE  device."
          ::= { pethNotificationControl 1 }

      pethNotificationControlEntry OBJECT-TYPE
          SYNTAX      PethNotificationControlEntry
          MAX-ACCESS  not-accessible
          STATUS      current
          DESCRIPTION
               "A set of objects that control the Notification events."
          INDEX    { pethNotificationControlGroupIndex }
          ::= { pethNotificationControlTable 1 }

      PethNotificationControlEntry ::= SEQUENCE {
          pethNotificationControlGroupIndex
              Integer32,
          pethNotificationControlEnable
                INTEGER
      }
        pethNotificationControlGroupIndex OBJECT-TYPE
          SYNTAX      Integer32 (1..2147483647)
          MAX-ACCESS  not-accessible
          STATUS      current
          DESCRIPTION
              "This variable uniquely identifies the group. Group means
              box in the stack, module in a rack and it is RECOMENDED
              that the value 1 be used for non-modular devices "
          ::= { pethNotificationControlEntry 1 }


         pethNotificationControlEnable  OBJECT-TYPE
             SYNTAX             INTEGER
                  {
                       enable(1),
                       disable(2)
                  }
             MAX-ACCESS         read-write
             STATUS             current
             DESCRIPTION
                  "Enable Notification from Agent"
          ::= { pethNotificationControlEntry 2 }
--
-- hsrpMgt
--

-- Subgroups
cHsrpGlobalConfig OBJECT IDENTIFIER ::= { hsrpMgt 1 }
cHsrpGroup        OBJECT IDENTIFIER ::= { hsrpMgt 2 }

-- Global Config Objects

cHsrpConfigTimeout OBJECT-TYPE
    SYNTAX Unsigned32(1..60)
    UNITS  "minutes"
    MAX-ACCESS read-write
    STATUS current
    DESCRIPTION
                "The amount of time in minutes a row in cHsrpGrpTable can
                 remain in a state other than active before being timed out."
    DEFVAL { 5 }
    ::= { cHsrpGlobalConfig 1 }
-- HSRP Tables

cHsrpGrpTable OBJECT-TYPE
    SYNTAX     SEQUENCE OF CHsrpGrpEntry
    MAX-ACCESS not-accessible
    STATUS     current
    DESCRIPTION
                "A table containing information on each HSRP group
                for each interface."
    ::= { cHsrpGroup 1 }


cHsrpGrpEntry OBJECT-TYPE
    SYNTAX     CHsrpGrpEntry
    MAX-ACCESS not-accessible
    STATUS     current
    DESCRIPTION
                "Information about an HSRP group. Management applications
                use cHsrpGrpRowStatus to control entry modification, creation
                and deletion.

                Setting cHsrpGrpRowStatus to 'active' causes the router to
                communicate using HSRP.

                The value of cHsrpGrpRowStatus may be set to 'destroy' at any
                time.

                Entries may not be created via SNMP without explicitly setting
                cHsrpGrpRowStatus to either 'createAndGo' or 'createAndWait'.

                Entries can be created and modified via the management
                protocol or by the device's local management interface.

                A management application wishing to create an entry should
                choose the ifIndex of the interface which is to be added
                as part of an HSRP group. Also, a cHsrpGrpNumber should
                be chosen. A group number is unique only amongst the groups
                on a particular interface. The value of the group number
                appears in packets which are transmitted and received on a
                LAN segment to which the router is connected. The application
                must select the group number as explained in the description
                for cHsrpGrpNumber.

                If the row is not active, and a local management interface
                command modifies that row, the row may transition to active
                state.

                A row which is not in active state will timeout after a
                configurable period (five minutes by default). This timeout
                period can be changed by setting cHsrpConfigTimeout."
    INDEX { ifIndex, cHsrpGrpNumber }
    ::= { cHsrpGrpTable 1 }

CHsrpGrpEntry ::=
    SEQUENCE {
                -- index
                cHsrpGrpNumber          Unsigned32,
                -- configuration items
                cHsrpGrpAuth            DisplayString,
                cHsrpGrpPriority        Unsigned32,
                cHsrpGrpPreempt         TruthValue,
                cHsrpGrpPreemptDelay        Unsigned32,

                cHsrpGrpUseConfiguredTimers     TruthValue,
                -- timers
                cHsrpGrpConfiguredHelloTime Unsigned32,
                cHsrpGrpConfiguredHoldTime  Unsigned32,
                cHsrpGrpLearnedHelloTime    Unsigned32,
                cHsrpGrpLearnedHoldTime     Unsigned32,
                -- status items
                cHsrpGrpVirtualIpAddr       IpAddress,
                cHsrpGrpUseConfigVirtualIpAddr  TruthValue,
                cHsrpGrpActiveRouter        IpAddress,
                cHsrpGrpStandbyRouter       IpAddress,
                cHsrpGrpStandbyState        HsrpState,
                cHsrpGrpVirtualMacAddr      MacAddress,
                cHsrpGrpEntryRowStatus      RowStatus
    }

cHsrpGrpNumber OBJECT-TYPE
    SYNTAX     Unsigned32(0..255)
    MAX-ACCESS not-accessible
    STATUS     current
    DESCRIPTION
                "This object along with the ifIndex of a particular interface
                uniquely identifies an HSRP group.

                Group numbers 0,1 and 2 are the only valid group numbers
                for TokenRing interfaces. For other media types, numbers
                range from 0 to 255. Each interface has its own set of group
                numbers. There's no relationship between the groups configured
                on different interfaces. Using a group number on one interface
                doesn't preclude using the same group number on a different
                interface. For example, there can be a group 1 on an Ethernet
                and a group 1 on Token Ring. More details can be found from
                RFC 2281."

    ::= { cHsrpGrpEntry 1 }

cHsrpGrpAuth OBJECT-TYPE
    SYNTAX     DisplayString (SIZE (0..8))
    MAX-ACCESS read-create
    STATUS     current
    DESCRIPTION
                "This is an unencrypted authentication string which is
                carried in all HSRP messages. An authentication string
                mismatch prevents a router interface from learning the
                designated IP address or HSRP timer values from
                other HSRP-enabled routers with the same group number.

                The function of this object is not to supply any sort of
                security-like authentication but rather to confirm that what's
                happening is what's intended. In other words, this is meant for
                sanity checking only."
    DEFVAL { "cisco" }
    ::= { cHsrpGrpEntry 2 }

cHsrpGrpPriority OBJECT-TYPE
    SYNTAX     Unsigned32(0..255)
    MAX-ACCESS read-create
    STATUS     current
    DESCRIPTION
                "The cHsrpGrpPriority helps to select the active
                and the standby routers. The router with the highest priority
                is selected as the active router. In the priority range of
                0 to 255, 0 is the lowest priority and 255 is the highest
                priority.

                If two (or more) routers in a group have the same priority,
                the one with the highest IP address of the interface is the
                active router. When the active router fails to send a Hello
                message within a configurable period of time, the standby
                router with the highest priority becomes the active router.

                A router with highest priority will only attempt to overthrow
                a lower priority active router if it is configured to preempt.
                But, if there is more than one router which is not active, the
                highest priority non-active router becomes the standby router."
    DEFVAL { 100 }
    ::= { cHsrpGrpEntry 3 }

cHsrpGrpPreempt OBJECT-TYPE
    SYNTAX     TruthValue
    MAX-ACCESS read-create
    STATUS     current
    DESCRIPTION
                "This object, if true, indicates that the current router
                should attempt to overthrow a lower priority active
                router and attempt to become the active router. If this
                object is false, the router will become the active router only
                if there is no such router (or if an active router fails)."
    DEFVAL { false }
    ::= { cHsrpGrpEntry 4 }

cHsrpGrpPreemptDelay OBJECT-TYPE
    SYNTAX     Unsigned32 (0..3600)
    UNITS      "seconds"
    MAX-ACCESS read-create
    STATUS     current
    DESCRIPTION
                 "This delay is the time difference between a router power up
                  and the time it can actually start preempting the currently
                  active router.

                  When a router first comes up, it doesn't have a complete
                  routing table. If it's configured to preempt, then it will
                  become the Active router, but it will not be able to provide
                  adequate routing services. The solution to this is to allow
                  for a configurable delay before the router actually preempts
                  the currently active router."
    DEFVAL { 0 }
    ::= { cHsrpGrpEntry 5 }

cHsrpGrpUseConfiguredTimers OBJECT-TYPE
    SYNTAX     TruthValue
        MAX-ACCESS read-only
        STATUS     current
        DESCRIPTION
                "HSRP routers learn a group's Hellotime or Holdtime from hello
                messages.

                The Hellotime is used to determine the frequency of
                generating hello messages when this router becomes the active
                or standby router. The Holdtime is the interval between the
                receipt of a Hello message and the presumption that the
                sending router has failed.

                If this object is true, the cHsrpGrpConfiguredHelloTime and
                cHsrpGrpConfiguredHoldTime will be used. If it is false,
                the Hellotime and Holdtime values are learned."
        ::= { cHsrpGrpEntry 6 }

cHsrpGrpConfiguredHelloTime OBJECT-TYPE
    SYNTAX     Unsigned32
    UNITS      "milliseconds"
    MAX-ACCESS read-create
    STATUS     current
    DESCRIPTION
                "If cHsrpGrpUseConfiguredTimers is true,
                cHsrpGrpConfiguredHelloTime is used when this router is an
                active router. Otherwise, the Hellotime learned from the
                current active router is used. All routers on a particular
                LAN segment must use the same Hellotime."
    DEFVAL { 3000 }
    ::= { cHsrpGrpEntry 7 }

cHsrpGrpConfiguredHoldTime OBJECT-TYPE
    SYNTAX     Unsigned32
    UNITS      "milliseconds"
    MAX-ACCESS read-create
    STATUS     current
    DESCRIPTION
                "If cHsrpGrpUseConfiguredTimers is true,
                cHsrpGrpConfiguredHoldTime is used when this router is an
                active router. Otherwise, the Holdtime learned from the
                current active router is used. All routers on a particular
                LAN segment should use the same Holdtime. Also, the Holdtime
                should be at least three times the value of the Hellotime and
                must be greater than the Hellotime."
    DEFVAL { 10000 }
    ::= { cHsrpGrpEntry 8 }

cHsrpGrpLearnedHelloTime OBJECT-TYPE
    SYNTAX     Unsigned32
    UNITS      "milliseconds"
    MAX-ACCESS read-only
    STATUS     current
    DESCRIPTION
                "If the Hellotime is not configured on a router, it can be
                learned from the Hello messages from active router, provided
                the Hello message is authenticated. If the Hellotime is not
                learned from a Hello message from the active router and it
                is not manually configured, a default value of 3 seconds is
                recommended."
    DEFVAL { 3000 }
    ::= { cHsrpGrpEntry 9 }

cHsrpGrpLearnedHoldTime OBJECT-TYPE
    SYNTAX     Unsigned32
    UNITS      "milliseconds"
    MAX-ACCESS read-only
    STATUS     current
    DESCRIPTION
                "If the Holdtime is not configured on a router, it can be
                learned from the Hello message from the active router.
                Holdtime should be learned only if the Hello message is
                authenticated. If the Holdtime is not learned and it is not
                manually configured, a default value of 10 seconds is
                recommended."
    DEFVAL { 10000 }
    ::= { cHsrpGrpEntry 10 }

cHsrpGrpVirtualIpAddr OBJECT-TYPE
    SYNTAX     IpAddress
    MAX-ACCESS read-create
    STATUS     current
    DESCRIPTION
                "This is the primary virtual IP address used by this group.
                If this address is configured (i.e a non zero IP address),
                this value is used. Otherwise, the agent will attempt to
                discover the virtual address through a discovery process
                (which scans the hello messages)."
        DEFVAL { '00000000'H }
    ::= { cHsrpGrpEntry 11 }

cHsrpGrpUseConfigVirtualIpAddr OBJECT-TYPE
    SYNTAX     TruthValue
        MAX-ACCESS read-only
        STATUS     current
        DESCRIPTION
                "If this object is true, cHsrpGrpVirtualIpAddr was a
                configured one. Otherwise, it indicates that
                cHsrpGrpVirtualIpAddr was a learned one."
    ::= { cHsrpGrpEntry 12 }

cHsrpGrpActiveRouter OBJECT-TYPE
    SYNTAX     IpAddress
    MAX-ACCESS read-only
    STATUS     current
    DESCRIPTION
                "IP Address of the currently active router for this group."
    ::= { cHsrpGrpEntry 13 }

cHsrpGrpStandbyRouter OBJECT-TYPE
    SYNTAX     IpAddress
    MAX-ACCESS read-only
    STATUS     current
    DESCRIPTION
                "IP Address of the currently standby router for this group."
    ::= { cHsrpGrpEntry 14 }

cHsrpGrpStandbyState OBJECT-TYPE
    SYNTAX     HsrpState
    MAX-ACCESS read-only
    STATUS     current
    DESCRIPTION
                 "The current HSRP state of this group on this interface."
    ::= { cHsrpGrpEntry 15 }

cHsrpGrpVirtualMacAddr OBJECT-TYPE
    SYNTAX     MacAddress
    MAX-ACCESS read-only
    STATUS     current
    DESCRIPTION
                "Mac Addresses used are as specified in RFC 2281. For ethernet
                and fddi interfaces, a MAC address will be in the range
                00:00:0c:07:ac:00 through 00:00:0c:07:ac:ff. The last octet is
                the hexadecimal equivalent of cHsrpGrpNumber (0-255).

                Some Ethernet and FDDI interfaces allow a unicast MAC address
                for each HSRP group. Certain Ethernet chipsets(LANCE Ethernet,
                VGANYLAN and QUICC Ethernet) only support a single Unicast
                Mac Address. In this case, only one HSRP group is allowed.

                For TokenRing interfaces, the following three MAC addresses
                are permitted (functional addresses):
                             C0:00:00:01:00:00
                             C0:00:00:02:00:00
                             C0:00:00:04:00:00."

    ::= { cHsrpGrpEntry 16 }

cHsrpGrpEntryRowStatus OBJECT-TYPE
    SYNTAX     RowStatus
    MAX-ACCESS read-create
    STATUS     current
    DESCRIPTION
                "The control that allows modification, creation, and deletion
                of entries.  For detailed rules see the DESCRIPTION for
                cHsrpGrpEntry."
    ::= {cHsrpGrpEntry 17 }

-- Extention group info
cHsrpExtGroup OBJECT IDENTIFIER ::= { hsrpMgt 3 }

cHsrpExtIfTrackedTable OBJECT-TYPE
    SYNTAX     SEQUENCE OF CHsrpExtIfTrackedEntry
    MAX-ACCESS not-accessible
    STATUS     current
    DESCRIPTION
         "A table containing information about tracked interfaces per
                  HSRP group."
    ::= { cHsrpExtGroup 1 }

cHsrpExtIfTrackedEntry OBJECT-TYPE
    SYNTAX     CHsrpExtIfTrackedEntry
    MAX-ACCESS not-accessible
    STATUS     current
    DESCRIPTION
                "The cHsrpExtIfTrackedEntry allows an HSRP group
                interface to track one or more interfaces. Weight(priority)
                is given to each and every interface tracked. When a tracked
                interface is unavailable, the HSRP priority of the router is
                decreased. i.e cHsrpGrpPriority value assigned to an HSRP
                group will reduce by the value assigned to
                cHsrpExtIfTrackedPriority. This reduces the likelihood
                of a router with a failed key interface becoming the
                active router.

                Setting cHsrpExtIfTrackedRowStatus to active starts
                the tracking of cHsrpExtIfTracked by the HSRP group.
                The value of cHsrpExtIfTrackedRowStatus may be set
                to destroy at any time.

                Entries may not be created via SNMP without explicitly setting
                cHsrpExtIfTrackedRowStatus to either 'createAndGo'
                or 'createAndWait'.

                Entries can be created and modified via the management
                protocol or by the device's local management interface.

                If the row is not active, and a local management interface
                command modifies that row, the row may transition to active
                state.

                A row entry in the cHsrpExtIfTrackedTable can not be created
                unless the corresponding row in the cHsrpGrpTable has been
                created. If that corresponding row in cHsrpGrpTable is
                deleted, the interfaces it tracks also get deleted.

                A row which is not in active state will timeout after a
                configurable period (five minutes by default). This timeout
                period can be changed by setting cHsrpConfigTimeout."
    INDEX { ifIndex, cHsrpGrpNumber, cHsrpExtIfTracked }
    ::= { cHsrpExtIfTrackedTable 1 }

CHsrpExtIfTrackedEntry ::=
    SEQUENCE {
                -- interface which is getting tracked
                cHsrpExtIfTracked       InterfaceIndex,
                -- Priority
                cHsrpExtIfTrackedPriority   Unsigned32,
                cHsrpExtIfTrackedRowStatus  RowStatus
    }

cHsrpExtIfTracked OBJECT-TYPE
    SYNTAX     InterfaceIndex
    MAX-ACCESS not-accessible
    STATUS     current
    DESCRIPTION
                  "Index into the cHsrpExtIfTrackedTable for the
                  corresponding { ifIndex, cHsrpGrpNumber } pair i.e for an
                  HSRP group. This is the ifIndex of the tracked interface."
    ::= { cHsrpExtIfTrackedEntry 1 }

cHsrpExtIfTrackedPriority OBJECT-TYPE
    SYNTAX     Unsigned32 (0..255)
    MAX-ACCESS read-create
    STATUS     current
    DESCRIPTION
                "Priority of the tracked interface for the corresponding
                { ifIndex, cHsrpGrpNumber } pair. In the range of 0 to 255, 0
                is the lowest priority and 255 is the highest. When a tracked
                interface is unavailable, the cHsrpGrpPriority of the router
                is decreased by the value of this object instance (If the
                cHsrpGrpPriority is less than the
                cHsrpExtIfTrackedPriority, then the HSRP priority
                becomes 0). This allows a standby router to be configured
                with a priority such that if the currently active router's
                priority is lowered because the tracked interface goes down,
                the standby router can takeover."
        DEFVAL { 0 }
    ::= { cHsrpExtIfTrackedEntry 2 }

cHsrpExtIfTrackedRowStatus OBJECT-TYPE
    SYNTAX     RowStatus
    MAX-ACCESS read-create
    STATUS     current
    DESCRIPTION
                "The control that allows modification, creation, and deletion
                 of entries. For detailed rules see the DESCRIPTION for
                 cHsrpExtIfTrackedEntry."
    ::= { cHsrpExtIfTrackedEntry 3 }

cHsrpExtSecAddrTable OBJECT-TYPE
    SYNTAX     SEQUENCE OF CHsrpExtSecAddrEntry
    MAX-ACCESS not-accessible
    STATUS     current
    DESCRIPTION
                "A table containing information about secondary HSRP IP
                Addresses per interface and group."
    ::= { cHsrpExtGroup 2 }

cHsrpExtSecAddrEntry OBJECT-TYPE
    SYNTAX     CHsrpExtSecAddrEntry
    MAX-ACCESS not-accessible
    STATUS     current
    DESCRIPTION
                "The CHsrpExtSecAddrEntry allows creation of secondary
                IP Addresses for each cHsrpGrpEntry row.

                Secondary addresses can be added by setting
                cHsrpExtSecAddrRowStatus to be active. The value of
                cHsrpExtSecAddrRowStatus may be set to destroy at any
                time.

                Entries may not be created via SNMP without explicitly setting
                cHsrpExtSecAddrRowStatus to either 'createAndGo'
                or 'createAndWait'.

                Entries can be created and modified via the management
                protocol or by the device's local management interface.

                If the row is not active, and a local management interface
                command modifies that row, the row may transition to active
                state.

                A row which is not in active state will timeout after a
                configurable period (five minutes by default). This timeout
                period can be changed by setting cHsrpConfigTimeout.

                Before creation of a cHsrpExtSecAddrEntry row,
                either cHsrpGrpConfiguredVirtualIpAddr or
                cHsrpGrpLearnedVirtualIpAddr must have a valid IP Address.
                This is because a secondary IP address cannot be created
                unless the primary IP address has already been set.

                To create a new cHsrpExtSecAddrEntry row, a management
                station should choose the ifIndex of the interface which is to
                be added as part of an HSRP group. Also, an HSRP group number
                and a cHsrpExtSecAddrAddress should be chosen.

                Deleting a {ifIndex, cHsrpGrpNumber} row in the
                cHsrpGrpTable will delete all corresponding
                rows in the cHsrpExtSecAddrTable.
                Deleting a primary address value in the cHsrpGrpEntry row
                will delete all secondary addresses for the same
                {ifIndex, cHsrpGrpNumber} pair."

    INDEX { ifIndex, cHsrpGrpNumber, cHsrpExtSecAddrAddress }
    ::= { cHsrpExtSecAddrTable 1 }

CHsrpExtSecAddrEntry ::=
    SEQUENCE {
                cHsrpExtSecAddrAddress      IpAddress,
                cHsrpExtSecAddrRowStatus    RowStatus
    }

cHsrpExtSecAddrAddress OBJECT-TYPE
       SYNTAX     IpAddress
       MAX-ACCESS not-accessible
       STATUS     current
       DESCRIPTION
              "A secondary IpAddress for the {ifIndex, cHsrpGrpNumber} pair.
               As explained in the DESCRIPTION for cHsrpExtSecAddrEntry, a
               primary address must exist before a secondary address for
               the same {ifIndex, cHsrpGrpNumber} pair can be created."
       ::= { cHsrpExtSecAddrEntry 1 }

cHsrpExtSecAddrRowStatus OBJECT-TYPE
    SYNTAX     RowStatus
    MAX-ACCESS read-create
    STATUS     current
    DESCRIPTION
                "The control that allows modification, creation, and deletion
                 of entries. For detailed rules see the DESCRIPTION for
                 cHsrpExtSecAddrEntry."
    ::= { cHsrpExtSecAddrEntry 2 }


--
--dot1dTpMgt
--

logicalPortTable  OBJECT-TYPE
    SYNTAX          SEQUENCE OF LogicalPortEntry
    MAX-ACCESS      not-accessible
    STATUS          current
    DESCRIPTION     "The conceptual table of logicalPortEntry."
    ::= { dot1dTpMgt 1 }

logicalPortEntry OBJECT-TYPE
    SYNTAX          LogicalPortEntry
    MAX-ACCESS      not-accessible
    STATUS          current
    DESCRIPTION     "The conceptual row for logicalPortTable."
    INDEX           { logicalPortIndex }
    ::= { logicalPortTable 1 }

LogicalPortEntry ::= SEQUENCE
    {
        logicalPortIndex              Integer32,
        logicalPortMaxDynamicMacCount Integer32
    }

logicalPortIndex  OBJECT-TYPE
        SYNTAX      Integer32
        MAX-ACCESS  not-accessible
        STATUS      current
        DESCRIPTION "The port and the trunk (not including trunk members) interface of
                     this logicalPortTable. The interface identified by a particular value
                     of this index is the same interface as identified by the same
                     value of ifIndex in the IF-MIB."
        ::= { logicalPortEntry 1 }

logicalPortMaxDynamicMacCount   OBJECT-TYPE
        SYNTAX      Integer32 (0..20)
        MAX-ACCESS  read-write
        STATUS      current
        DESCRIPTION "The max number of mac addresses that a port is allowed to learn."
        ::= { logicalPortEntry 2 }


--
--amapMgt
--

-- amapConfiguration

amapState OBJECT-TYPE
        SYNTAX      INTEGER
                    {
                        active(1),
                        inactive(2)
                    }
        MAX-ACCESS  read-write
        STATUS      current
        DESCRIPTION "Current state of the AMAP agent."
        DEFVAL      { active }
        ::= { amapMgt 1 }

amapDiscoveryTime OBJECT-TYPE
        SYNTAX      INTEGER (1..65535)
        MAX-ACCESS  read-write
        STATUS      current
        DESCRIPTION "The time in seconds for interval between hello
                     packets in the initial discovery phase of the
                     AMAP protocol."
        DEFVAL      { 30 }
        ::= { amapMgt 2 }

amapCommonTime OBJECT-TYPE
        SYNTAX      INTEGER (1..65535)
        MAX-ACCESS  read-write
        STATUS      current
        DESCRIPTION "The time in seconds for the interval between
                     hello packets at other than the discovery phase."
        DEFVAL      { 300 }
        ::= { amapMgt 3 }

-- amapTrapElements

amapLastTrapReason OBJECT-TYPE
        SYNTAX      INTEGER
                    {
                        add(1),
                        change(2),
                        remove(3),
                        none(4)
                    }
        MAX-ACCESS  read-only
        STATUS      current
        DESCRIPTION "Reason for last change of port status. Valid
                     reasons are:
                     1 - port added
                     2 - change of information on existing port
                     3 - port deleted
                     4 - no trap has been sent"
        ::= { amapMgt 4 }

amapLastTrapPort OBJECT-TYPE
        SYNTAX      INTEGER (0..65535)
        MAX-ACCESS  read-only
        STATUS      current
        DESCRIPTION "The ifindex number of the port that most recently
                     changed."
        ::= { amapMgt 5 }

-- amapPortConnectionTable

amapPortConnectionTable OBJECT-TYPE
        SYNTAX      SEQUENCE OF AmapPortConnectionEntry
        MAX-ACCESS  not-accessible
        STATUS      current
        DESCRIPTION "AMAP adjacent switch,local and remote
                     connection index,and Vlan information."
        ::= { amapMgt 6 }

amapPortConnectionEntry OBJECT-TYPE
        SYNTAX      AmapPortConnectionEntry
        MAX-ACCESS  not-accessible
        STATUS      current
        DESCRIPTION "AMAP adjacent switch,local and remote
                     connection index,and Vlan information."
        INDEX       { amapLocalConnectIndex,
                      amapRemMac,
                      amapRemConnectIndex }
        ::= { amapPortConnectionTable 1 }

AmapPortConnectionEntry ::= SEQUENCE
{
    amapLocalConnectIndex   INTEGER,
    amapRemMac              MacAddress,
    amapRemConnectIndex     INTEGER,
    amapRemVlan             INTEGER,
    amapRemHostName         OCTET STRING (SIZE (32)),
    amapLocalIfindex        InterfaceIndex,
    amapLocalSlot           INTEGER,
    amapLocalPort           INTEGER,
    amapRemSlot             INTEGER,
    amapRemPort             INTEGER
}

amapLocalConnectIndex OBJECT-TYPE
        SYNTAX      INTEGER (0..65535)
        MAX-ACCESS  read-only
        STATUS      current
        DESCRIPTION "The local index number of a connection in the
                     local switch which has an adjacent switch connected.
                     This index is assigned to a connection by the AMAP
                     application running on the local switch."
        ::= { amapPortConnectionEntry 1 }

amapRemMac OBJECT-TYPE
        SYNTAX      MacAddress
        MAX-ACCESS  read-only
        STATUS      current
        DESCRIPTION "The MAC Address of the CMM in the adjacent switch."
        ::= { amapPortConnectionEntry 2 }

amapRemConnectIndex OBJECT-TYPE
        SYNTAX      INTEGER (0..65535)
        MAX-ACCESS  read-only
        STATUS      current
        DESCRIPTION "The remote index number of the connection in the
                     adjacent switch to which the local switch has a
                     connection connected.This index is assigned to a
                     connection by the AMAP application running on the
                     adjacent switch."
        ::= { amapPortConnectionEntry 3 }

amapRemVlan OBJECT-TYPE
        SYNTAX      INTEGER (0..65535)
        MAX-ACCESS  read-only
        STATUS      current
        DESCRIPTION "The remote Vlan to which the connection is
                     connected in the adjacent switch."
        ::= { amapPortConnectionEntry 4 }

amapRemHostName OBJECT-TYPE
        SYNTAX      OCTET STRING (SIZE (32))
        MAX-ACCESS  read-only
        STATUS      current
        DESCRIPTION "The remote hostname for the adjacent switch."
        ::= { amapPortConnectionEntry 5 }

amapLocalIfindex OBJECT-TYPE
        SYNTAX      InterfaceIndex
        MAX-ACCESS  read-only
        STATUS      current
        DESCRIPTION "The local ifindex of the port to which the connection
                     is connected."
        ::= { amapPortConnectionEntry 6 }

amapLocalSlot OBJECT-TYPE
        SYNTAX      INTEGER (0..65535)
        MAX-ACCESS  read-only
        STATUS      current
        DESCRIPTION "The local slot of the port to which the connection
                     is connected."
        ::= { amapPortConnectionEntry 7 }

amapLocalPort OBJECT-TYPE
        SYNTAX      INTEGER (0..65535)
        MAX-ACCESS  read-only
        STATUS      current
        DESCRIPTION "The local interface port of the port to which the
                     connection is connected."
        ::= { amapPortConnectionEntry 8 }

amapRemSlot OBJECT-TYPE
        SYNTAX      INTEGER (0..65535)
        MAX-ACCESS  read-only
        STATUS      current
        DESCRIPTION "The remote slot of the port to which the connection
                     is connected."
        ::= { amapPortConnectionEntry 9 }

amapRemPort OBJECT-TYPE
        SYNTAX      INTEGER (0..65535)
        MAX-ACCESS  read-only
        STATUS      current
        DESCRIPTION "The remote interface port of the port to which the
                     connection is connected."
        ::= { amapPortConnectionEntry 10 }

--amapHostsTable

amapHostsTable OBJECT-TYPE
        SYNTAX      SEQUENCE OF AmapHostEntry
        MAX-ACCESS  not-accessible
        STATUS      current
        DESCRIPTION "AMAP adjacent switch IP address information."
        ::= { amapMgt 7 }

amapHostEntry OBJECT-TYPE
        SYNTAX      AmapHostEntry
        MAX-ACCESS  not-accessible
        STATUS      current
        DESCRIPTION "AMAP adjacent switch IP address information."
        INDEX       { amapHostMac,
                      amapIpAddr }
        ::= { amapHostsTable 1 }

AmapHostEntry ::= SEQUENCE
{
    amapHostMac             MacAddress,
    amapIpAddr              IpAddress
}

amapHostMac OBJECT-TYPE
        SYNTAX      MacAddress
        MAX-ACCESS  read-only
        STATUS      current
        DESCRIPTION "The MAC Address of the CMM in the adjacent switch."
        ::= { amapHostEntry 1 }

amapIpAddr OBJECT-TYPE
        SYNTAX      IpAddress
        MAX-ACCESS  read-only
        STATUS      current
        DESCRIPTION "An IP address of the adjacent switch."
        ::= { amapHostEntry 2 }


--
-- multicastStormMgt
--

multicastStormMgt   OBJECT IDENTIFIER ::= { stormMgt 1 }

multicastStormTable OBJECT-TYPE
        SYNTAX      SEQUENCE OF MulticastStormEntry
        MAX-ACCESS  not-accessible
        STATUS      current
        DESCRIPTION "Table of descriptive and status information about the
                     configuration of each switch port (including expansion slot)
                     in this system."
        ::= { multicastStormMgt 1 }

multicastStormEntry OBJECT-TYPE
        SYNTAX      MulticastStormEntry
        MAX-ACCESS  not-accessible
        STATUS      current
        DESCRIPTION "An entry in the table, containing information
                     about the configuration of one switch port on the switch."
        INDEX       { multicastStormIfIndex }
        ::= { multicastStormTable 1 }

MulticastStormEntry ::= SEQUENCE
{
    multicastStormIfIndex      Integer32,
    multicastStormStatus       INTEGER,
    multicastStormPktRate      Integer32
}

multicastStormIfIndex OBJECT-TYPE
        SYNTAX      Integer32
        MAX-ACCESS  not-accessible
        STATUS      current
        DESCRIPTION "This is defined as ifIndex in the IF-MIB."
        ::= { multicastStormEntry 1 }

multicastStormStatus OBJECT-TYPE
        SYNTAX      INTEGER
                    {
                        enabled(1),
                        disabled(2)
                    }
        MAX-ACCESS  read-write
        STATUS      current
        DESCRIPTION "Whether multicast storm protection is enabled."
        ::= { multicastStormEntry 2 }

multicastStormPktRate OBJECT-TYPE
        SYNTAX      Integer32(1..1488000)
        MAX-ACCESS  read-write
        STATUS      current
        DESCRIPTION "Multicast storm threshold as packets per second.
                     Multicast and broadcast use the same threshold
                     setting, so when the user sets it, the broadcast rate will effect
                     the mulitcast rate, and vice versa. If the user enables multicast storm control,
                     broadcast storm control will be enabled implicitly if not yet enabled.
                     Multicast strom control also counts broadcast frames as multicast frames."
        ::= { multicastStormEntry 4 }

--
-- unicastStormMgt
--

unicastStormMgt     OBJECT IDENTIFIER ::= { stormMgt 2 }

unicastStormTable OBJECT-TYPE
        SYNTAX      SEQUENCE OF UnicastStormEntry
        MAX-ACCESS  not-accessible
        STATUS      current
        DESCRIPTION "Table of descriptive and status information about the
                     configuration of each switch port (including the expansion slot)
                     in this system."
        ::= { unicastStormMgt 1 }

unicastStormEntry OBJECT-TYPE
        SYNTAX      UnicastStormEntry
        MAX-ACCESS  not-accessible
        STATUS      current
        DESCRIPTION "An entry in the table, containing information
                     about the configuration of one switch port on the switch."
        INDEX       { unicastStormIfIndex }
        ::= { unicastStormTable 1 }

UnicastStormEntry ::= SEQUENCE
{
    unicastStormIfIndex      Integer32,
    unicastStormStatus       INTEGER,
    unicastStormPktRate      Integer32
}

unicastStormIfIndex OBJECT-TYPE
        SYNTAX      Integer32
        MAX-ACCESS  not-accessible
        STATUS      current
        DESCRIPTION "This is defined as ifIndex in the IF-MIB."
        ::= { unicastStormEntry 1 }

unicastStormStatus OBJECT-TYPE
        SYNTAX      INTEGER
                    {
                        enabled(1),
                        disabled(2)
                    }
        MAX-ACCESS  read-write
        STATUS      current
        DESCRIPTION "Whether unicast storm protection is enabled."
        ::= { unicastStormEntry 2 }

unicastStormPktRate OBJECT-TYPE
        SYNTAX      Integer32(1..32)
        MAX-ACCESS  read-write
        STATUS      current
        DESCRIPTION "The unidcast storm threshold is 64K packets per second.
                     If this entry is for a trunk, this is the value
                     for each member port."
        ::= { unicastStormEntry 4 }

--
-- unknownUcastStormMgt
--
unknownUcastStormMgt OBJECT IDENTIFIER ::=  {stormMgt 4 }

unknownUcastStormTable  OBJECT-TYPE
    SYNTAX      SEQUENCE OF UnknownUcastStormEntry
    MAX-ACCESS  not-accessible
    STATUS      current
    DESCRIPTION "Table to manage the unknown unicast storm control."
    ::= { unknownUcastStormMgt 1 }

unknownUcastStormEntry  OBJECT-TYPE
    SYNTAX      UnknownUcastStormEntry
    MAX-ACCESS  not-accessible
    STATUS      current
    DESCRIPTION "The conceptual row of unknownUcastStormTable."
    INDEX       { unknownUcastStormIfIndex }
    ::= { unknownUcastStormTable 1 }

UnknownUcastStormEntry  ::= SEQUENCE
{
    unknownUcastStormIfIndex    Integer32,
    unknownUcastStormStatus     EnabledStatus,
    unknownUcastStormSampleType INTEGER,
    unknownUcastStormPktRate    INTEGER,
    unknownUcastStormOctetRate  INTEGER,
    unknownUcastStormPercent    INTEGER
}

unknownUcastStormIfIndex    OBJECT-TYPE
    SYNTAX      Integer32
    MAX-ACCESS  not-accessible
    STATUS      current
    DESCRIPTION "The port or trunk interface of the portTable. The interface
                 identified by a particular value of this index is the same
                 interface as identified by the same value of ifIndex in the
                 IF-MIB."
    ::= { unknownUcastStormEntry 1 }

unknownUcastStormStatus     OBJECT-TYPE
    SYNTAX      EnabledStatus
    MAX-ACCESS  read-write
    STATUS      current
    DESCRIPTION "The parameter indicates that the unknown unicast
                 storm protection is enabled/disabled."
    ::= { unknownUcastStormEntry 2 }

unknownUcastStormSampleType OBJECT-TYPE
    SYNTAX      INTEGER {packet-rate(1), octet-rate(2), percent(3)}
    MAX-ACCESS  read-write
    STATUS      current
    DESCRIPTION "The parameter indicates which storm protection mode is used."
    ::= { unknownUcastStormEntry 3 }

unknownUcastStormPktRate    OBJECT-TYPE
    SYNTAX      INTEGER
    MAX-ACCESS  read-write
    STATUS      current
    DESCRIPTION "The parameter indicates the packet rate of the storm protection."
    ::= { unknownUcastStormEntry 4 }

unknownUcastStormOctetRate  OBJECT-TYPE
    SYNTAX      INTEGER
    MAX-ACCESS  read-write
    STATUS      current
    DESCRIPTION "The parameter indicates the byte rate of the storm protection."
    ::= { unknownUcastStormEntry 5 }

unknownUcastStormPercent    OBJECT-TYPE
    SYNTAX      INTEGER
    MAX-ACCESS  read-write
    STATUS      current
    DESCRIPTION "The parameter indicates the traffic percentage of the storm protection."
    ::= { unknownUcastStormEntry 6 }

--
-- Auto Traffic Control ASE3528B-E1-FLF-P5-00011
--
atcMgt OBJECT IDENTIFIER ::= { stormMgt 5 }

atcBcastStormTcApplyTime       OBJECT-TYPE
    SYNTAX      Integer32
    MAX-ACCESS  read-write
    STATUS      current
    DESCRIPTION "The parameter indicates the timing when the ATC (Auto
                 Traffic Control) is activated after the broadcast traffic
                 being detected as the storm."
    ::= { atcMgt 1 }

atcBcastStormTcReleaseTime       OBJECT-TYPE
    SYNTAX      Integer32
    MAX-ACCESS  read-write
    STATUS      current
    DESCRIPTION "The parameter indicates the timing when the ATC is released
                 after the broadcast traffic being detected as no storm."
    ::= { atcMgt 2 }

atcBcastStormTable      OBJECT-TYPE
    SYNTAX      SEQUENCE OF AtcBcastStormEntry
    MAX-ACCESS  not-accessible
    STATUS      current
    DESCRIPTION "The table contains the Auto Traffic Control configuration
                 and the status for broadcast traffic."
    ::= { atcMgt 3 }

atcBcastStormEntry      OBJECT-TYPE
    SYNTAX      AtcBcastStormEntry
    MAX-ACCESS  not-accessible
    STATUS      current
    DESCRIPTION "The conceptual row of the table."
    INDEX       { atcBcastStormIfIndex }
    ::= { atcBcastStormTable 1 }

AtcBcastStormEntry ::= SEQUENCE
{
    atcBcastStormIfIndex                Integer32,
    atcBcastStormEnable                 EnabledStatus,
    atcBcastStormAutoRelease            EnabledStatus,
    atcBcastStormSampleType             INTEGER,
    atcBcastStormCurrentTrafficRate     Integer32,
    atcBcastStormAlarmFireThreshold     Integer32,
    atcBcastStormAlarmClearThreshold    Integer32,
    atcBcastStormTcAction               INTEGER,
    atcBcastStormAlarmFireTrapStatus    EnabledStatus,
    atcBcastStormAlarmClearTrapStatus   EnabledStatus,
    atcBcastStormTcApplyTrapStatus      EnabledStatus,
    atcBcastStormTcReleaseTrapStatus    EnabledStatus
}

atcBcastStormIfIndex        OBJECT-TYPE
    SYNTAX      Integer32
    MAX-ACCESS  accessible-for-notify
    STATUS      current
    DESCRIPTION "The specified port on which the ATC is applied."
    ::= { atcBcastStormEntry 1 }

atcBcastStormEnable     OBJECT-TYPE
    SYNTAX      EnabledStatus
    MAX-ACCESS  read-write
    STATUS      current
    DESCRIPTION "The parameter indicates whether the ATC of the broadcast
                 traffic is applied."
    ::= { atcBcastStormEntry 2 }

atcBcastStormAutoRelease    OBJECT-TYPE
    SYNTAX      EnabledStatus
    MAX-ACCESS  read-write
    STATUS      current
    DESCRIPTION "The parameter indicates whether the Auto-Release feature
                 of ATC is applied."
    ::= { atcBcastStormEntry 3 }

atcBcastStormSampleType     OBJECT-TYPE
    SYNTAX      INTEGER
                {
                    packet-rate(1),
                    octet-rate(2),
                    percent(3)
                }
    MAX-ACCESS  read-write
    STATUS      current
    DESCRIPTION "The parameter indicates the unit of traffic rate and threshold."
    ::= { atcBcastStormEntry 4 }
atcBcastStormCurrentTrafficRate OBJECT-TYPE
    SYNTAX      Integer32
    MAX-ACCESS  read-only
    STATUS      current
    DESCRIPTION "The parameter indicates the current broadcast traffic rate."
    ::= { atcBcastStormEntry 5 }

atcBcastStormAlarmFireThreshold OBJECT-TYPE
    SYNTAX      Integer32
    MAX-ACCESS  read-write
    STATUS      current
    DESCRIPTION "The parameter indicates that if the current broadcast traffic rate
                exceeds the specified threshold, it will be treated as the storm."
    ::= { atcBcastStormEntry 6 }

atcBcastStormAlarmClearThreshold OBJECT-TYPE
    SYNTAX      Integer32
    MAX-ACCESS  read-write
    STATUS      current
    DESCRIPTION "The parameter indicates that if the current broadcast traffic
                 falls below the specified threshold it will be treated as the
                 normal traffic."
    ::= { atcBcastStormEntry 7 }

atcBcastStormTcAction OBJECT-TYPE
    SYNTAX      INTEGER
                {
                    rate-control(1),
                    shutdown(2)
                }
    MAX-ACCESS  read-write
    STATUS      current
    DESCRIPTION "The parameter indicates the protecting action which
                 ATC will applied to the specified port."
    ::= { atcBcastStormEntry 8 }

atcBcastStormAlarmFireTrapStatus    OBJECT-TYPE
    SYNTAX      EnabledStatus
    MAX-ACCESS  read-write
    STATUS      current
    DESCRIPTION "The parameter indicates whether the trap has
                 to be sent when the broadcast storm has been detected."
    ::= { atcBcastStormEntry 9 }

atcBcastStormAlarmClearTrapStatus    OBJECT-TYPE
    SYNTAX      EnabledStatus
    MAX-ACCESS  read-write
    STATUS      current
    DESCRIPTION "The parameter indicates whether the trap has
                 to be sent when the broadcast storm has been detected as
                 the normal traffic."
    ::= { atcBcastStormEntry 10 }

atcBcastStormTcApplyTrapStatus     OBJECT-TYPE
    SYNTAX      EnabledStatus
    MAX-ACCESS  read-write
    STATUS      current
    DESCRIPTION "The parameter indicates whether the trap has to be sent when
                 the ATC is activated."
    ::= { atcBcastStormEntry 11 }

atcBcastStormTcReleaseTrapStatus    OBJECT-TYPE
    SYNTAX      EnabledStatus
    MAX-ACCESS  read-write
    STATUS      current
    DESCRIPTION "The parameter indicates whether the trap has to be sent when
                 the ATC is released."
    ::= { atcBcastStormEntry 12 }

atcMcastStormTcApplyTime   OBJECT-TYPE
    SYNTAX      INTEGER
    MAX-ACCESS  read-write
    STATUS      current
    DESCRIPTION "The parameter indicates the timing when the ATC (Auto
                 Traffic Control) is activated after the broadcast traffic
                 being detected as the storm."
    ::= { atcMgt 4 }

atcMcastStormTcReleaseTime  OBJECT-TYPE
    SYNTAX      INTEGER
    MAX-ACCESS  read-write
    STATUS      current
    DESCRIPTION "The parameter indicates the timing when the ATC is released
                 after the broadcast traffic being detected as no storm."
    ::= { atcMgt 5 }

atcMcastStormTable      OBJECT-TYPE
    SYNTAX      SEQUENCE OF AtcMcastStormEntry
    MAX-ACCESS  not-accessible
    STATUS      current
    DESCRIPTION "The table contains the Auto Traffic Control configuration
                 and the status for mulicast traffic."
    ::= { atcMgt 6 }

atcMcastStormEntry      OBJECT-TYPE
    SYNTAX      AtcMcastStormEntry
    MAX-ACCESS  not-accessible
    STATUS      current
    DESCRIPTION "The conceptual row of the table."
    INDEX       { atcMcastStormIfIndex }
    ::= { atcMcastStormTable 1 }

AtcMcastStormEntry ::= SEQUENCE
{
    atcMcastStormIfIndex                Integer32,
    atcMcastStormEnable                 EnabledStatus,
    atcMcastStormAutoRelease            EnabledStatus,
    atcMcastStormSampleType             INTEGER,
    atcMcastStormCurrentTrafficRate     Integer32,
    atcMcastStormAlarmFireThreshold         Integer32,
    atcMcastStormAlarmClearThreshold         Integer32,
    atcMcastStormTcAction               INTEGER,
    atcMcastStormAlarmFireTrapStatus        EnabledStatus,
    atcMcastStormAlarmClearTrapStatus        EnabledStatus,
    atcMcastStormTcApplyTrapStatus         EnabledStatus,
    atcMcastStormTcReleaseTrapStatus    EnabledStatus
}

atcMcastStormIfIndex        OBJECT-TYPE
    SYNTAX      Integer32
    MAX-ACCESS  accessible-for-notify
    STATUS      current
    DESCRIPTION "The specified port on which the ATC is applied."
    ::= { atcMcastStormEntry 1 }

atcMcastStormEnable     OBJECT-TYPE
    SYNTAX      EnabledStatus
    MAX-ACCESS  read-write
    STATUS      current
    DESCRIPTION "The parameter indicates whether the ATC of the mulicast
                 traffic is applied."
    ::= { atcMcastStormEntry 2 }

atcMcastStormAutoRelease    OBJECT-TYPE
    SYNTAX      EnabledStatus
    MAX-ACCESS  read-write
    STATUS      current
    DESCRIPTION "The parameter indicates whether the Auto-Release feature
                 of ATC is applied."
    ::= { atcMcastStormEntry 3 }

atcMcastStormSampleType     OBJECT-TYPE
    SYNTAX      INTEGER
                {
                    packet-rate(1),
                    octet-rate(2),
                    percent(3)
                }
    MAX-ACCESS  read-write
    STATUS      current
    DESCRIPTION "The parameter indicates the unit of traffic rate and threshold."
    ::= { atcMcastStormEntry 4 }
atcMcastStormCurrentTrafficRate OBJECT-TYPE
    SYNTAX      Integer32
    MAX-ACCESS  read-only
    STATUS      current
    DESCRIPTION "The parameter indicates the current mulicast traffic rate."
    ::= { atcMcastStormEntry 5 }

atcMcastStormAlarmFireThreshold OBJECT-TYPE
    SYNTAX      Integer32
    MAX-ACCESS  read-write
    STATUS      current
    DESCRIPTION "The parameter indicates that if the current mulicast traffic rate
                exceeds the specified threshold, it will be treated as the storm."
    ::= { atcMcastStormEntry 6 }

atcMcastStormAlarmClearThreshold OBJECT-TYPE
    SYNTAX      Integer32
    MAX-ACCESS  read-write
    STATUS      current
    DESCRIPTION "The parameter indicates that if the current mulicast traffic
                 falls below the specified threshold it will be treated as the
                 normal traffic."
    ::= { atcMcastStormEntry 7 }

atcMcastStormTcAction OBJECT-TYPE
    SYNTAX      INTEGER
                {
                    rate-control(1),
                    shutdown(2)
                }
    MAX-ACCESS  read-write
    STATUS      current
    DESCRIPTION "The parameter indicates the protecting action which
                 ATC will applied to the specified port."
    ::= { atcMcastStormEntry 8 }

atcMcastStormAlarmFireTrapStatus    OBJECT-TYPE
    SYNTAX      EnabledStatus
    MAX-ACCESS  read-write
    STATUS      current
    DESCRIPTION "The parameter indicates whether the trap has
                 to be sent when the mulicast storm has been detected."
    ::= { atcMcastStormEntry 9 }

atcMcastStormAlarmClearTrapStatus    OBJECT-TYPE
    SYNTAX      EnabledStatus
    MAX-ACCESS  read-write
    STATUS      current
    DESCRIPTION "The parameter indicates whether the trap has
                 to be sent when the mulicast storm has been detected as
                 the normal traffic."
    ::= { atcMcastStormEntry 10 }

atcMcastStormTcApplyTrapStatus     OBJECT-TYPE
    SYNTAX      EnabledStatus
    MAX-ACCESS  read-write
    STATUS      current
    DESCRIPTION "The parameter indicates whether the trap has to be sent when
                 the ATC is activated."
    ::= { atcMcastStormEntry 11 }

atcMcastStormTcReleaseTrapStatus    OBJECT-TYPE
    SYNTAX      EnabledStatus
    MAX-ACCESS  read-write
    STATUS      current
    DESCRIPTION "The parameter indicates whether the trap has to be sent when
                 the ATC is released."
    ::= { atcMcastStormEntry 12 }

--
-- alertLedMgt
--

alertLedAdminStatus OBJECT-TYPE
        SYNTAX      EnabledStatus
        MAX-ACCESS  read-write
        STATUS      current
        DESCRIPTION "Set this object to enabled(1) to enable Alert LED.
                     Set this object to disabled(2) to disabled Alert LED.
                     If the Alert LED function is enabled and active,
                     then the Alert LED on the device will be on."
        ::= { alertLedMgt 1 }

alertLedOperStatus OBJECT-TYPE
        SYNTAX      INTEGER
                    {
                        active(1),
                        deactive(2)
                    }
        MAX-ACCESS  read-only
        STATUS      current
        DESCRIPTION "This object is active(1) when the alert condition
                     is active. This object is inactive(2) when the alert
                     condition is inactive. If the Alert LED function is
                     enabled and active, then the Alert LED on the device
                     will be on."
        ::= { alertLedMgt 2 }

alertLedAcknowledge OBJECT-TYPE
        SYNTAX      INTEGER
                    {
                        acknowledge(1),
                        noAcknowledge(2)
                    }
        MAX-ACCESS  read-write
        STATUS      current
        DESCRIPTION "When the Alert LED condition is latched, set this
                     object to acknowledge(1) to acknowledge the condition
                     and clear the latch. When the Alert LED condition is
                     not latched, setting this object to acknowledge(1) has
                     no effect. In any case, setting this object to noAcknowledge(2)
                     has no effect. When read, this object always has a value of
                     noAcknowledge(2)."
        ::= { alertLedMgt 3 }

--
--sbcMgt
--

sbcIpAddress  OBJECT-TYPE
    SYNTAX     IpAddress
    MAX-ACCESS read-write
    STATUS     current
    DESCRIPTION
        "The IP Address of SBC."
    ::= { sbcMgt 1 }

--
--mvrMgt
--

mvrStatus OBJECT-TYPE
        SYNTAX      EnabledStatus
        MAX-ACCESS  read-write
        STATUS      current
        DESCRIPTION "Parameter to enable or disable MVR(Multicast VLAN
                     Registration) on the device. NOTE: IGMP Snooping
                     must be enabled first before enabling MVR and MVR
                     will be disabled when IGMP Snooping is disabled."
        ::= { mvrMgt 1 }

mvrVlanId OBJECT-TYPE
        SYNTAX      Integer32
        MAX-ACCESS  read-write
        STATUS      current
        DESCRIPTION "To set VLAN for MVR.The VLAN identified by a particular
                     value of this index is the same VLAN as identified by the
                     same value of dot1qVlanIndex in the Q-BRIDGE-MIB."
        ::= { mvrMgt 2 }

mvrMaxGroups  OBJECT-TYPE
        SYNTAX      Integer32
        MAX-ACCESS  read-only
        STATUS      current
        DESCRIPTION "The maximum number of MVR groups."
        ::= { mvrMgt 3 }

mvrCurrentGroups   OBJECT-TYPE
        SYNTAX      Integer32
        MAX-ACCESS  read-only
        STATUS      current
        DESCRIPTION "The current number of MVR groups."
        ::= { mvrMgt 4}

mvrGroupsCtl      OBJECT IDENTIFIER   ::= { mvrMgt 5 }

mvrGroupsCtlId   OBJECT-TYPE
        SYNTAX      IpAddress
        MAX-ACCESS  read-write
        STATUS      current
        DESCRIPTION "The start of a contiguous range of MVR group
                     addresses."
        ::= { mvrGroupsCtl 1 }

mvrGroupsCtlCount   OBJECT-TYPE
        SYNTAX      Integer32
        MAX-ACCESS  read-write
        STATUS      current
        DESCRIPTION "The range count for configuring MVR group addresses."
        ::= { mvrGroupsCtl 2 }

mvrGroupsCtlAction   OBJECT-TYPE
        SYNTAX      INTEGER
        {
            noAction(0),
            create(1),
            destory(2)
        }
        MAX-ACCESS  read-write
        STATUS      current
        DESCRIPTION "Sets the configure action for a contiguous range of MVR group
                     addresses. The start addresses is the current value of
                     mvrGroupsCtlId and the range count is the current value of
                     mvrGroupsCtlCount. Set this object to create(2) to
                     create MVR group addresses. Set this object
                     to destory(3) to delete MVR group addresses. When
                     the action is complete, this object becomes noAction(1)."
        ::= { mvrGroupsCtl 3 }

mvrGroupTable OBJECT-TYPE
       SYNTAX      SEQUENCE OF MvrGroupEntry
       MAX-ACCESS  not-accessible
       STATUS      current
       DESCRIPTION "The table for configuring the MVR group."
       ::= { mvrMgt 6 }

mvrGroupEntry OBJECT-TYPE
       SYNTAX      MvrGroupEntry
       MAX-ACCESS  not-accessible
       STATUS      current
       DESCRIPTION "The entry for configuring the MVR group."
       INDEX  {mvrGroupId}
       ::= { mvrGroupTable 1 }

MvrGroupEntry ::= SEQUENCE
{
    mvrGroupId IpAddress,
    mvrGroutActive INTEGER,
    mvrGroupStatus INTEGER
}

mvrGroupId OBJECT-TYPE
        SYNTAX      IpAddress
        MAX-ACCESS  not-accessible
        STATUS      current
        DESCRIPTION "The multicast address of the MVR group."
        ::= { mvrGroupEntry 1 }

mvrGroutActive   OBJECT-TYPE
        SYNTAX      INTEGER
        {
            active(1),
            inactive(2)
        }
        MAX-ACCESS  read-only
        STATUS      current
        DESCRIPTION "To indicate if the group has a member or not. If there are no
                     members, the status is inactive(2); otherwise the status
                     is active(1)."
        ::= { mvrGroupEntry 2 }

mvrGroupStatus   OBJECT-TYPE
        SYNTAX      INTEGER
        {
            valid(1),
            invalid(2)
        }
        MAX-ACCESS  read-write
        STATUS      current
        DESCRIPTION "Setting this to valid(1) creates an entry. Setting this
                     to invalid(2) destroys an entry."
        ::= { mvrGroupEntry 3 }

mvrGroupStaticTable   OBJECT-TYPE
        SYNTAX      SEQUENCE OF MvrGroupStaticEntry
        MAX-ACCESS  not-accessible
        STATUS      current
        DESCRIPTION "The table for configuring the static members of the
                     MVR group."
        ::= { mvrMgt 7 }

mvrGroupStaticEntry OBJECT-TYPE
       SYNTAX      MvrGroupStaticEntry
       MAX-ACCESS  not-accessible
       STATUS      current
       DESCRIPTION "The entry for configuring the static members of the
                    MVR group."
       INDEX  {mvrGroupStaticAddress}
       ::= { mvrGroupStaticTable 1 }

MvrGroupStaticEntry ::= SEQUENCE
{
    mvrGroupStaticAddress   IpAddress,
    mvrGroupStaticPorts     PortList,
    mvrGroupStaticStatus    INTEGER

}

mvrGroupStaticAddress  OBJECT-TYPE
        SYNTAX      IpAddress
        MAX-ACCESS  not-accessible
        STATUS      current
        DESCRIPTION "The multicast address of the MVR group."
        ::= { mvrGroupStaticEntry 1 }

mvrGroupStaticPorts  OBJECT-TYPE
        SYNTAX      PortList
        MAX-ACCESS  read-write
        STATUS      current
        DESCRIPTION "The set of ports configured by management in this entry.
                     Ports entered in this list will be the static members
                     of this MVR group."
        ::= { mvrGroupStaticEntry 2 }

mvrGroupStaticStatus  OBJECT-TYPE
        SYNTAX      INTEGER
        {
            valid(1),
            invalid(2)
        }
        MAX-ACCESS  read-write
        STATUS      current
        DESCRIPTION "Setting this to valid(1) creates an entry. Setting this
                     to invalid(2) destroys an entry."
        ::= { mvrGroupStaticEntry 3 }

mvrGroupCurrentTable   OBJECT-TYPE
        SYNTAX      SEQUENCE OF MvrGroupCurrentEntry
        MAX-ACCESS  not-accessible
        STATUS      current
        DESCRIPTION "The table for the current members of the MVR group."
        ::= { mvrMgt 8 }

mvrGroupCurrentEntry OBJECT-TYPE
       SYNTAX      MvrGroupCurrentEntry
       MAX-ACCESS  not-accessible
       STATUS      current
       DESCRIPTION "The entry for the current members of the MVR group."
       INDEX  {mvrGroupCurrentAddress}
       ::= { mvrGroupCurrentTable 1 }

MvrGroupCurrentEntry ::= SEQUENCE
{
    mvrGroupCurrentAddress  IpAddress,
    mvrGroupCurrentPorts    PortList
}

mvrGroupCurrentAddress   OBJECT-TYPE
        SYNTAX      IpAddress
        MAX-ACCESS  not-accessible
        STATUS      current
        DESCRIPTION "The multicast address of the MVR group."
        ::= { mvrGroupCurrentEntry 1 }

mvrGroupCurrentPorts   OBJECT-TYPE
        SYNTAX      PortList
        MAX-ACCESS  read-only
        STATUS      current
        DESCRIPTION "The complete set of ports currently associated with this
                     MVR group."
        ::= { mvrGroupCurrentEntry 2 }

mvrPortTable   OBJECT-TYPE
        SYNTAX      SEQUENCE OF MvrPortEntry
        MAX-ACCESS  not-accessible
        STATUS      current
        DESCRIPTION "The table for configuring the MVR port."
        ::= { mvrMgt 9 }

mvrPortEntry OBJECT-TYPE
       SYNTAX      MvrPortEntry
       MAX-ACCESS  not-accessible
       STATUS      current
       DESCRIPTION "The entry for configuring the MVR port."
       INDEX  {mvrIfIndex}
       ::= { mvrPortTable 1 }

MvrPortEntry ::= SEQUENCE
{
    mvrIfIndex  InterfaceIndex,
    mvrPortType INTEGER,
    mvrPortImmediateLeave   EnabledStatus,
    mvrPortActive   INTEGER

}

mvrIfIndex   OBJECT-TYPE
        SYNTAX      InterfaceIndex
        MAX-ACCESS  not-accessible
        STATUS      current
        DESCRIPTION "The port interface of the portTable. The interface
                     identified by a particular value of this index is the
                     same interface as identified by the same value of ifIndex
                     in the IF-MIB."
        ::= { mvrPortEntry 1 }

mvrPortType   OBJECT-TYPE
        SYNTAX      INTEGER
        {
            none(0),
            source(1),
            receiver(2)
        }
        MAX-ACCESS  read-write
        STATUS      current
        DESCRIPTION "For configuring the MVR port type. To disable the MVR
                     port type, use the none(0)."
        ::= { mvrPortEntry 2 }

mvrPortImmediateLeave   OBJECT-TYPE
        SYNTAX      EnabledStatus
        MAX-ACCESS  read-write
        STATUS      current
        DESCRIPTION "To enable immediate leave on MVR port."
        ::= { mvrPortEntry 3 }

mvrPortActive   OBJECT-TYPE
        SYNTAX      INTEGER
        {
            active(1),
            inactive(2)
        }
        MAX-ACCESS  read-only
        STATUS      current
        DESCRIPTION "To indicate if the port is associated with the MVR group.
                     If the port is the MVR receiver port or the MVR source
                     port in MVR vlan, the status is active(1); otherwise
                     the status is inactive(2)."
        ::= { mvrPortEntry 4 }

multipleMvrMgt        OBJECT IDENTIFIER ::= { mvrMgt 11 }

multipleMvrTable OBJECT-TYPE
       SYNTAX      SEQUENCE OF MultipleMvrEntry
       MAX-ACCESS  not-accessible
       STATUS      current
       DESCRIPTION "The table for configuring the MVR domain."
       ::= { multipleMvrMgt 1 }

multipleMvrEntry OBJECT-TYPE
       SYNTAX      MultipleMvrEntry
       MAX-ACCESS  not-accessible
       STATUS      current
       DESCRIPTION "The entry for configuring the MVR domain."
       INDEX  {multipleMvrDomainId}
       ::= { multipleMvrTable 1 }

MultipleMvrEntry ::= SEQUENCE
{
    multipleMvrDomainId          INTEGER,
    multipleMvrVlanId            INTEGER,
    multipleMvrMaxGroups         INTEGER,
    multipleMvrCurrentGroups     INTEGER,
    multipleMvrRunningStatus     TruthValue,
    multipleMvrStatus            EnabledStatus
}

multipleMvrDomainId   OBJECT-TYPE
        SYNTAX      INTEGER
        MAX-ACCESS  not-accessible
        STATUS      current
        DESCRIPTION "The ID of the MVR domain."
        ::= { multipleMvrEntry 1 }

multipleMvrVlanId OBJECT-TYPE
        SYNTAX      INTEGER
        MAX-ACCESS  read-write
        STATUS      current
        DESCRIPTION "To set VLAN for MVR.The VLAN identified by a particular
                     value of this index is the same VLAN as identified by the
                     same value of dot1qVlanIndex in the Q-BRIDGE-MIB."
        ::= { multipleMvrEntry 2 }

multipleMvrMaxGroups  OBJECT-TYPE
        SYNTAX      INTEGER
        MAX-ACCESS  read-only
        STATUS      current
        DESCRIPTION "The maximum number of MVR groups."
        ::= { multipleMvrEntry 3 }

multipleMvrCurrentGroups   OBJECT-TYPE
        SYNTAX      INTEGER
        MAX-ACCESS  read-only
        STATUS      current
        DESCRIPTION "The current number of MVR groups."
        ::= { multipleMvrEntry 4}

multipleMvrRunningStatus OBJECT-TYPE
        SYNTAX  TruthValue
        MAX-ACCESS  read-only
        STATUS      current
        DESCRIPTION "Describes the running status of MVR (Multicast VLAN Registration)
                     to the switch. A value of true(1) indicates that all necessary
                     conditions in the MVR environment are satisfied. A value of false(2)
                     indicates that some necessary conditions in the MVR environment are
                     not satisfied."
        ::= { multipleMvrEntry 5 }

multipleMvrStatus OBJECT-TYPE
        SYNTAX      EnabledStatus
        MAX-ACCESS  read-write
        STATUS      current
        DESCRIPTION "Parameter to enable or disable MVR(Multicast VLAN
                     Registration) on the device. NOTE: IGMP Snooping
                     must be enabled first before enabling MVR and MVR
                     will be disabled when IGMP Snooping is disabled."
        ::= { multipleMvrEntry 6 }

multipleMvrGroupsCtl      OBJECT IDENTIFIER   ::= { multipleMvrMgt 2 }

multipleMvrGroupsCtlDomainId   OBJECT-TYPE
        SYNTAX      Integer32
        MAX-ACCESS  read-write
        STATUS      current
        DESCRIPTION "The ID of the MVR domain."
        ::= { multipleMvrGroupsCtl 1 }

multipleMvrGroupsCtlGroupId   OBJECT-TYPE
        SYNTAX      IpAddress
        MAX-ACCESS  read-write
        STATUS      current
        DESCRIPTION "The start of a contiguous range of MVR group
                     addresses."
        ::= { multipleMvrGroupsCtl 2 }

multipleMvrGroupsCtlCount   OBJECT-TYPE
        SYNTAX      Integer32
        MAX-ACCESS  read-write
        STATUS      current
        DESCRIPTION "The range count for configuring MVR group addresses."
        ::= { multipleMvrGroupsCtl 3 }

multipleMvrGroupsCtlAction   OBJECT-TYPE
        SYNTAX      INTEGER
        {
            noAction(0),
            create(1),
            destory(2)
        }
        MAX-ACCESS  read-write
        STATUS      current
        DESCRIPTION "Sets the configure action for a contiguous range of MVR group
                     addresses. The start addresses is the current value of
                     mvrGroupsCtlId and the range count is the current value of
                     mvrGroupsCtlCount. Set this object to create(2) to
                     create MVR group addresses. Set this object
                     to destory(3) to delete MVR group addresses. When
                     the action is complete, this object becomes noAction(1)."
        ::= { multipleMvrGroupsCtl 4 }

multipleMvrGroupTable OBJECT-TYPE
       SYNTAX      SEQUENCE OF MultipleMvrGroupEntry
       MAX-ACCESS  not-accessible
       STATUS      current
       DESCRIPTION "The table for configuring the MVR group."
       ::= { multipleMvrMgt 3 }

multipleMvrGroupEntry OBJECT-TYPE
       SYNTAX      MultipleMvrGroupEntry
       MAX-ACCESS  not-accessible
       STATUS      current
       DESCRIPTION "The entry for configuring the MVR group."
       INDEX  {multipleMvrGroupDomainId, multipleMvrGroupId}
       ::= { multipleMvrGroupTable 1 }

MultipleMvrGroupEntry ::= SEQUENCE
{
    multipleMvrGroupDomainId   INTEGER,
    multipleMvrGroupId         IpAddress,
    multipleMvrGroupActive     INTEGER,
    multipleMvrGroupStatus     INTEGER
}

multipleMvrGroupDomainId   OBJECT-TYPE
        SYNTAX      INTEGER
        MAX-ACCESS  not-accessible
        STATUS      current
        DESCRIPTION "The ID of the MVR domain."
        ::= { multipleMvrGroupEntry 1 }

multipleMvrGroupId OBJECT-TYPE
        SYNTAX      IpAddress
        MAX-ACCESS  not-accessible
        STATUS      current
        DESCRIPTION "The multicast address of the MVR group."
        ::= { multipleMvrGroupEntry 2 }

multipleMvrGroupActive   OBJECT-TYPE
        SYNTAX      INTEGER
        {
            active(1),
            inactive(2)
        }
        MAX-ACCESS  read-only
        STATUS      current
        DESCRIPTION "To indicate if the group has a member or not. If there are no
                     members, the status is inactive(2); otherwise the status
                     is active(1)."
        ::= { multipleMvrGroupEntry 3 }

multipleMvrGroupStatus   OBJECT-TYPE
        SYNTAX      ValidStatus
        MAX-ACCESS  read-write
        STATUS      current
        DESCRIPTION "Setting this to valid(1) creates an entry. Setting this
                     to invalid(2) destroys an entry."
        ::= { multipleMvrGroupEntry 4 }

multipleMvrGroupStaticTable   OBJECT-TYPE
        SYNTAX      SEQUENCE OF MultipleMvrGroupStaticEntry
        MAX-ACCESS  not-accessible
        STATUS      current
        DESCRIPTION "The table for configuring the static members of the
                     MVR group."
        ::= { multipleMvrMgt 4 }

multipleMvrGroupStaticEntry OBJECT-TYPE
       SYNTAX      MvrGroupStaticEntry
       MAX-ACCESS  not-accessible
       STATUS      current
       DESCRIPTION "The entry for configuring the static members of the
                    MVR group."
       INDEX  {multipleMvrGroupStaticDomainId, multipleMvrGroupStaticAddress}
       ::= { multipleMvrGroupStaticTable 1 }

MultipleMvrGroupStaticEntry ::= SEQUENCE
{
    multipleMvrGroupStaticDomainId  INTEGER,
    multipleMvrGroupStaticAddress   IpAddress,
    multipleMvrGroupStaticPorts     PortList,
    multipleMvrGroupStaticStatus    INTEGER

}

multipleMvrGroupStaticDomainId   OBJECT-TYPE
        SYNTAX      INTEGER
        MAX-ACCESS  not-accessible
        STATUS      current
        DESCRIPTION "The ID of the MVR domain."
        ::= { multipleMvrGroupStaticEntry 1 }

multipleMvrGroupStaticAddress  OBJECT-TYPE
        SYNTAX      IpAddress
        MAX-ACCESS  not-accessible
        STATUS      current
        DESCRIPTION "The multicast address of the MVR group."
        ::= { multipleMvrGroupStaticEntry 2 }

multipleMvrGroupStaticPorts  OBJECT-TYPE
        SYNTAX      PortList
        MAX-ACCESS  read-write
        STATUS      current
        DESCRIPTION "The set of ports configured by management in this entry.
                     Ports entered in this list will be the static members
                     of this MVR group."
        ::= { multipleMvrGroupStaticEntry 3 }

multipleMvrGroupStaticStatus  OBJECT-TYPE
        SYNTAX      ValidStatus
        MAX-ACCESS  read-write
        STATUS      current
        DESCRIPTION "Setting this to valid(1) creates an entry. Setting this
                     to invalid(2) destroys an entry."
        ::= { multipleMvrGroupStaticEntry 4 }

multipleMvrGroupCurrentTable   OBJECT-TYPE
        SYNTAX      SEQUENCE OF MultipleMvrGroupCurrentEntry
        MAX-ACCESS  not-accessible
        STATUS      current
        DESCRIPTION "The table for the current members of the MVR group."
        ::= { multipleMvrMgt 5 }

multipleMvrGroupCurrentEntry OBJECT-TYPE
       SYNTAX      MultipleMvrGroupCurrentEntry
       MAX-ACCESS  not-accessible
       STATUS      current
       DESCRIPTION "The entry for the current members of the MVR group."
       INDEX  {multipleMvrGroupCurrentDomainId, multipleMvrGroupCurrentAddress}
       ::= { multipleMvrGroupCurrentTable 1 }

MultipleMvrGroupCurrentEntry ::= SEQUENCE
{
    multipleMvrGroupCurrentDomainId  INTEGER,
    multipleMvrGroupCurrentAddress   IpAddress,
    multipleMvrGroupCurrentPorts     PortList
}

multipleMvrGroupCurrentDomainId   OBJECT-TYPE
        SYNTAX      INTEGER
        MAX-ACCESS  not-accessible
        STATUS      current
        DESCRIPTION "The ID of the MVR domain."
        ::= { multipleMvrGroupCurrentEntry 1 }

multipleMvrGroupCurrentAddress   OBJECT-TYPE
        SYNTAX      IpAddress
        MAX-ACCESS  not-accessible
        STATUS      current
        DESCRIPTION "The multicast address of the MVR group."
        ::= { multipleMvrGroupCurrentEntry 2 }

multipleMvrGroupCurrentPorts   OBJECT-TYPE
        SYNTAX      PortList
        MAX-ACCESS  read-only
        STATUS      current
        DESCRIPTION "The complete set of ports currently associated with this
                     MVR group."
        ::= { multipleMvrGroupCurrentEntry 3 }

multipleMvrPortTable   OBJECT-TYPE
        SYNTAX      SEQUENCE OF MultipleMvrPortEntry
        MAX-ACCESS  not-accessible
        STATUS      current
        DESCRIPTION "The table for configuring the MVR port."
        ::= { multipleMvrMgt 6 }

multipleMvrPortEntry OBJECT-TYPE
       SYNTAX      MultipleMvrPortEntry
       MAX-ACCESS  not-accessible
       STATUS      current
       DESCRIPTION "The entry for configuring the MVR port."
       INDEX  {multipleMvrIfIndex, multipleMvrPortDomainId}
       ::= { multipleMvrPortTable 1 }

MultipleMvrPortEntry ::= SEQUENCE
{
    multipleMvrIfIndex              InterfaceIndex,
    multipleMvrPortDomainId         INTEGER,
    multipleMvrPortType             INTEGER,
    multipleMvrPortImmediateLeave   EnabledStatus,
    multipleMvrPortActive           INTEGER
}

multipleMvrIfIndex   OBJECT-TYPE
        SYNTAX      InterfaceIndex
        MAX-ACCESS  not-accessible
        STATUS      current
        DESCRIPTION "The port interface of the portTable. The interface
                     identified by a particular value of this index is the
                     same interface as identified by the same value of ifIndex
                     in the IF-MIB."
        ::= { multipleMvrPortEntry 1 }

multipleMvrPortDomainId   OBJECT-TYPE
        SYNTAX      INTEGER
        MAX-ACCESS  not-accessible
        STATUS      current
        DESCRIPTION "The ID of the MVR domain."
        ::= { multipleMvrPortEntry 2 }

multipleMvrPortType   OBJECT-TYPE
        SYNTAX      INTEGER
        {
            none(0),
            source(1),
            receiver(2)
        }
        MAX-ACCESS  read-write
        STATUS      current
        DESCRIPTION "For configuring the MVR port type. To disable the MVR
                     port type, use the none(0)."
        ::= { multipleMvrPortEntry 3 }

multipleMvrPortImmediateLeave   OBJECT-TYPE
        SYNTAX      EnabledStatus
        MAX-ACCESS  read-write
        STATUS      current
        DESCRIPTION "To enable immediate leave on MVR port."
        ::= { multipleMvrPortEntry 4 }

multipleMvrPortActive   OBJECT-TYPE
        SYNTAX      INTEGER
        {
            active(1),
            inactive(2)
        }
        MAX-ACCESS  read-only
        STATUS      current
        DESCRIPTION "To indicate if the port is associated with the MVR group.
                     If the port is the MVR receiver port or the MVR source
                     port in MVR vlan, the status is active(1); otherwise
                     the status is inactive(2)."
        ::= { multipleMvrPortEntry 5 }

--
-- egressPacketBlockMgt
--
egressPacketBlockUnknownMcastTable OBJECT-TYPE
        SYNTAX      SEQUENCE OF EgressPacketBlockUnknownMcastEntry
        MAX-ACCESS  not-accessible
        STATUS      current
        DESCRIPTION "Table to manage the control of unknown multicast egress
                     packet block for ports."
        ::= { egressPacketBlockMgt 1 }

egressPacketBlockUnknownMcastEntry OBJECT-TYPE
        SYNTAX      EgressPacketBlockUnknownMcastEntry
        MAX-ACCESS  not-accessible
        STATUS      current
        DESCRIPTION "The conceptual row of egressPacketBlockUnknownMcastTable."
        INDEX       { egressPacketBlockUnknownMcastIfIndex }
        ::= { egressPacketBlockUnknownMcastTable 1 }

EgressPacketBlockUnknownMcastEntry ::= SEQUENCE
{
    egressPacketBlockUnknownMcastIfIndex      InterfaceIndex,
    egressPacketBlockUnknownMcastStatus       EnabledStatus
}

egressPacketBlockUnknownMcastIfIndex OBJECT-TYPE
        SYNTAX      InterfaceIndex
        MAX-ACCESS  not-accessible
        STATUS      current
        DESCRIPTION "The port and the trunk interface of the portTable. The interface
                     identified by a particular value of this index is the same
                     interface as identified by the same value of ifIndex in the
                     IF-MIB."
        ::= { egressPacketBlockUnknownMcastEntry 1 }

egressPacketBlockUnknownMcastStatus OBJECT-TYPE
        SYNTAX      EnabledStatus
        MAX-ACCESS  read-write
        STATUS      current
        DESCRIPTION "Whether unknown multicast egress packet block protection is enabled."
        ::= { egressPacketBlockUnknownMcastEntry 2 }

egressPacketBlockUnknownUcastTable OBJECT-TYPE
        SYNTAX      SEQUENCE OF EgressPacketBlockUnknownUcastEntry
        MAX-ACCESS  not-accessible
        STATUS      current
        DESCRIPTION "Table to manage the control of unknown unicast egress
                     packet block for ports."
        ::= { egressPacketBlockMgt 2 }

egressPacketBlockUnknownUcastEntry OBJECT-TYPE
        SYNTAX      EgressPacketBlockUnknownUcastEntry
        MAX-ACCESS  not-accessible
        STATUS      current
        DESCRIPTION "The conceptual row of unknownUcastTable."
        INDEX       { egressPacketBlockUnknownUcastIfIndex }
        ::= { egressPacketBlockUnknownUcastTable 1 }

EgressPacketBlockUnknownUcastEntry ::= SEQUENCE
{
    egressPacketBlockUnknownUcastIfIndex      InterfaceIndex,
    egressPacketBlockUnknownUcastStatus       EnabledStatus
}

egressPacketBlockUnknownUcastIfIndex OBJECT-TYPE
        SYNTAX      InterfaceIndex
        MAX-ACCESS  not-accessible
        STATUS      current
        DESCRIPTION "The port and the trunk interface of the portTable. The
                     interface identified by a particular value of this index
                     is the same interface as identified by the same value
                     of ifIndex in the IF-MIB."
        ::= { egressPacketBlockUnknownUcastEntry 1 }

egressPacketBlockUnknownUcastStatus OBJECT-TYPE
        SYNTAX      EnabledStatus
        MAX-ACCESS  read-write
        STATUS      current
        DESCRIPTION "Whether unknown unicast egress packet block protection
                     is enabled."
        ::= { egressPacketBlockUnknownUcastEntry 2 }

-- ---------------------------------------------------------------------

--
-- dhcpSnoopMgt
--

-- Management of DHCP snooping and IP souce guard.

dhcpSnoopGlobal         OBJECT IDENTIFIER ::= { dhcpSnoopMgt 1 }
dhcpSnoopVlan           OBJECT IDENTIFIER ::= { dhcpSnoopMgt 2 }
dhcpSnoopInterface      OBJECT IDENTIFIER ::= { dhcpSnoopMgt 3 }
dhcpSnoopBindings       OBJECT IDENTIFIER ::= { dhcpSnoopMgt 4 }
dhcpSnoopStatistics     OBJECT IDENTIFIER ::= { dhcpSnoopMgt 5 }

dhcpSnoopEnable  OBJECT-TYPE
        SYNTAX     EnabledStatus
        MAX-ACCESS  read-write
        STATUS      current
        DESCRIPTION "This object indicates whether the DHCP Snooping feature is
                     enabled."
        ::= { dhcpSnoopGlobal 1 }

dhcpSnoopVerifyMacAddressEnable     OBJECT-TYPE
        SYNTAX     EnabledStatus
        MAX-ACCESS  read-write
        STATUS      current
        DESCRIPTION "This object indicates whether DHCP Snooping Mac address
                     verification is enabled."
        ::= { dhcpSnoopGlobal 2 }

dhcpSnoopInformationOptionEnable  OBJECT-TYPE

        SYNTAX     EnabledStatus
        MAX-ACCESS  read-write
        STATUS      current
        DESCRIPTION "This object indicates whether the DHCP snooping information option(option 82) feature is
                     enabled."
        ::= { dhcpSnoopGlobal 3 }

dhcpSnoopInformationOptionPolicy     OBJECT-TYPE
        SYNTAX     INTEGER
                    {
                        drop(1),
                        keep(2),
                        replace(3)
                    }
        MAX-ACCESS  read-write
        STATUS      current
        DESCRIPTION "This object indicates which reforwarding policy shall be used for DHCP
                     snooping information option(option 82). A value of drop(1) means to drop
                     the DHCP request packet which has the information option(option 82).
                     A value of keep(2) means to keep the existing information option(option 82)
                     of the DHCP request packet. A value of replace(3), which is the default value,
                     means to replace the existing information option(option 82) of the DHCP
                     request packet."
        ::= { dhcpSnoopGlobal 4 }

--
dhcpSnoopVlanConfigTable    OBJECT-TYPE
        SYNTAX      SEQUENCE OF DhcpSnoopVlanConfigEntry
        MAX-ACCESS  not-accessible
        STATUS      current
        DESCRIPTION "A table contains DHCP Snooping configurations of existing VLANs."
        ::= { dhcpSnoopVlan 1 }

dhcpSnoopVlanConfigEntry    OBJECT-TYPE
        SYNTAX      DhcpSnoopVlanConfigEntry
        MAX-ACCESS  not-accessible
        STATUS      current
        DESCRIPTION "An instance contains the configuration to enable
                     or disable DHCP Snooping at each existing VLAN."
        INDEX       { dhcpSnoopVlanIndex }
        ::= { dhcpSnoopVlanConfigTable 1 }

DhcpSnoopVlanConfigEntry  ::= SEQUENCE
{
        dhcpSnoopVlanIndex      VlanIndex,
        dhcpSnoopVlanEnable     EnabledStatus
}

dhcpSnoopVlanIndex      OBJECT-TYPE
        SYNTAX      VlanIndex
        MAX-ACCESS  not-accessible
        STATUS      current
        DESCRIPTION "This object indicates the VLAN ID on which DHCP Snooping
                     feature is configured."
        ::= { dhcpSnoopVlanConfigEntry 1 }

dhcpSnoopVlanEnable     OBJECT-TYPE
        SYNTAX     EnabledStatus
        MAX-ACCESS  read-write
        STATUS      current
        DESCRIPTION "This object indicates whether DHCP Snooping is enabled in
                     this VLAN."
        ::= { dhcpSnoopVlanConfigEntry 2 }

--
dhcpSnoopPortConfigTable    OBJECT-TYPE
        SYNTAX      SEQUENCE OF DhcpSnoopPortConfigEntry
        MAX-ACCESS  not-accessible
        STATUS      current
        DESCRIPTION "A table provides the mechanism to configure the trust
                     state of each port or trunk for DHCP Snooping purpose."
        ::= { dhcpSnoopInterface 1 }

dhcpSnoopPortConfigEntry    OBJECT-TYPE
        SYNTAX      DhcpSnoopPortConfigEntry
        MAX-ACCESS  not-accessible
        STATUS      current
        DESCRIPTION "An instance contains the configuration to enable or disable
                     trust state of each port or trunk for DHCP Snooping purpose."
        INDEX       { dhcpSnoopPortIfIndex }
        ::= { dhcpSnoopPortConfigTable 1 }

DhcpSnoopPortConfigEntry    ::= SEQUENCE
{
        dhcpSnoopPortIfIndex        InterfaceIndex,
        dhcpSnoopPortTrustEnable    EnabledStatus
}

dhcpSnoopPortIfIndex        OBJECT-TYPE
        SYNTAX      InterfaceIndex
        MAX-ACCESS  not-accessible
        STATUS      current
        DESCRIPTION "The ifIndex value of the port or trunk."
        ::= { dhcpSnoopPortConfigEntry 1 }

dhcpSnoopPortTrustEnable    OBJECT-TYPE
        SYNTAX     EnabledStatus
        MAX-ACCESS  read-write
        STATUS      current
        DESCRIPTION "This object indicates whether the port or trunk is trusted
                     for DHCP Snooping purpose."
        ::= { dhcpSnoopPortConfigEntry 2 }
--
dhcpSnoopBindingsTable      OBJECT-TYPE
        SYNTAX      SEQUENCE OF DhcpSnoopBindingsEntry
        MAX-ACCESS  not-accessible
        STATUS      current
        DESCRIPTION "A table contains the DHCP bindings information learnt by
                     the device."
        ::= { dhcpSnoopBindings 1 }

dhcpSnoopBindingsEntry      OBJECT-TYPE
        SYNTAX      DhcpSnoopBindingsEntry
        MAX-ACCESS  not-accessible
        STATUS      current
        DESCRIPTION "An instance contains the Mac address, IP address type,
                     IP address, VLAN number, interface number, leased time and
                     status."
        INDEX       { dhcpSnoopBindingsVlanIndex, dhcpSnoopBindingsMacAddress }
        ::= { dhcpSnoopBindingsTable 1 }

DhcpSnoopBindingsEntry      ::= SEQUENCE
{
        dhcpSnoopBindingsVlanIndex      VlanIndex,
        dhcpSnoopBindingsMacAddress     MacAddress,
        dhcpSnoopBindingsAddrType       InetAddressType,
        dhcpSnoopBindingsEntryType      INTEGER,
        dhcpSnoopBindingsIpAddress      IpAddress,
        dhcpSnoopBindingsPortIfIndex    InterfaceIndex,
        dhcpSnoopBindingsLeaseTime      Unsigned32
}

dhcpSnoopBindingsVlanIndex      OBJECT-TYPE
        SYNTAX      VlanIndex
        MAX-ACCESS  not-accessible
        STATUS      current
        DESCRIPTION "This object indicates the VLAN which a DHCP client host
                     belongs to."
        ::= { dhcpSnoopBindingsEntry 1 }

dhcpSnoopBindingsMacAddress     OBJECT-TYPE
        SYNTAX      MacAddress
        MAX-ACCESS  not-accessible
        STATUS      current
        DESCRIPTION "This object indicates the MAC address of a DHCP client
                     host."
        ::= { dhcpSnoopBindingsEntry 2 }

dhcpSnoopBindingsAddrType       OBJECT-TYPE
        SYNTAX      InetAddressType
        MAX-ACCESS  read-only
        STATUS      current
        DESCRIPTION "This object indicates the type of IP address denoted in
                     dhcpSnoopBindingsIpAddress type."
        ::= { dhcpSnoopBindingsEntry 3 }

dhcpSnoopBindingsEntryType      OBJECT-TYPE
        SYNTAX      INTEGER { dynamic(1), static(2) }
        MAX-ACCESS  read-only
        STATUS      current
        DESCRIPTION "This object indicates that this binding is obtained from
                     dynamically learning or is a static configuraion."
        ::= { dhcpSnoopBindingsEntry 4 }

dhcpSnoopBindingsIpAddress      OBJECT-TYPE
        SYNTAX      IpAddress
        MAX-ACCESS  read-only
        STATUS      current
        DESCRIPTION "This object indicates the allocated IP address of
                     a DHCP client host."
        ::= { dhcpSnoopBindingsEntry 5 }

dhcpSnoopBindingsPortIfIndex    OBJECT-TYPE
        SYNTAX      InterfaceIndex
        MAX-ACCESS  read-only
        STATUS      current
        DESCRIPTION "This object indicates the port or trunk where a DHCP client
                     host connects to."
        ::= { dhcpSnoopBindingsEntry 6 }

dhcpSnoopBindingsLeaseTime      OBJECT-TYPE
        SYNTAX      Unsigned32
        MAX-ACCESS  read-only
        STATUS      current
        DESCRIPTION "This object indicates the leased time of this DHCP
                     bindings."
        ::= { dhcpSnoopBindingsEntry 7 }

--

dhcpSnoopTotalForwardedPkts     OBJECT-TYPE
        SYNTAX      Counter32
        MAX-ACCESS  read-only
        STATUS      current
        DESCRIPTION "Indicates the total number of packets subjected to
                     DHCP Snooping is forwarded."
        ::= { dhcpSnoopStatistics 1 }

dhcpSnoopTotalDroppedPkts       OBJECT-TYPE
        SYNTAX      Counter32
        MAX-ACCESS  read-only
        STATUS      current
        DESCRIPTION "Indicates the total number of packets subjected to
                     DHCP Snooping is dropped."
        ::= { dhcpSnoopStatistics 2 }

dhcpSnoopUntrustedPortDroppedPkts   OBJECT-TYPE
        SYNTAX      Counter32
        MAX-ACCESS  read-only
        STATUS      current
        DESCRIPTION "Indicates the number of packets subjected to DHCP Snooping
                     is dropped because they come from untrusted interface."
        ::= { dhcpSnoopStatistics 3 }

--
-- clusterMgt
--

clusterEnable  OBJECT-TYPE
    SYNTAX     EnabledStatus
    MAX-ACCESS read-write
    STATUS     current
    DESCRIPTION
        "Enables or disables clustering on the device."
    ::= { clusterMgt 1 }

clusterCommanderEnable  OBJECT-TYPE
    SYNTAX     EnabledStatus
    MAX-ACCESS read-write
    STATUS     current
    DESCRIPTION
        "Enables or disables the device as commander in a cluster."
    ::= { clusterMgt 2 }

clusterIpPool  OBJECT-TYPE
    SYNTAX     IpAddress
    MAX-ACCESS read-write
    STATUS     current
    DESCRIPTION
        "The start internal IP address of a cluster pool."
    ::= { clusterMgt 4 }

clusterClearCandidateTable  OBJECT-TYPE
    SYNTAX     INTEGER
    					 {
    					     noClear(1),
    					     clear(2)
    					 }
    MAX-ACCESS read-write
    STATUS     current
    DESCRIPTION
        "Setting this object to clear(2) starts to clear the candidate table."
    ::= { clusterMgt 5 }

clusterRole  OBJECT-TYPE
    SYNTAX     INTEGER
               {
                   commander(1),
                   candidate(2),
                   activeMember(3),
                   disabled(5)
               }
    MAX-ACCESS read-only
    STATUS     current
    DESCRIPTION
        "The current role of the device in a cluster.
             commander(1)   : The switch is the controlling device in a
                              cluster.
             candidate(2)   : The switch has been discovered by the commander,
                              but it has not been manually configured
                              for access from the commander.
             activeMember(3): The switch has been manually configured for access
                              from the commander and it is active
                              in the cluster.
             disabled(5)     : The switch has clustering disabled."
    ::= { clusterMgt 6 }

clusterMemberCount  OBJECT-TYPE
    SYNTAX     Counter32
    MAX-ACCESS read-only
    STATUS     current
    DESCRIPTION
        "The total number of members in a cluster."
    ::= { clusterMgt 7 }

clusterCandidateCount  OBJECT-TYPE
    SYNTAX     Counter32
    MAX-ACCESS read-only
    STATUS     current
    DESCRIPTION
        "The total number of candidates in a cluster."
    ::= { clusterMgt 8 }

clusterCandidateTable OBJECT-TYPE
    SYNTAX     SEQUENCE OF ClusterCandidateEntry
    MAX-ACCESS not-accessible
    STATUS     current
    DESCRIPTION
        "A table listing cluster candidates."
    ::= { clusterMgt 9 }

clusterCandidateEntry OBJECT-TYPE
    SYNTAX     ClusterCandidateEntry
    MAX-ACCESS not-accessible
    STATUS     current
    DESCRIPTION
        "A conceptual row containing the information of the candidate."
    INDEX { clusterCandidateMacAddr}
    ::= { clusterCandidateTable 1 }

ClusterCandidateEntry ::=
    SEQUENCE {
                clusterCandidateMacAddr  MacAddress,
                clusterCandidateDesc     DisplayString,
                clusterCandidateRole     INTEGER
    }

clusterCandidateMacAddr OBJECT-TYPE
       SYNTAX     MacAddress
       MAX-ACCESS not-accessible
       STATUS     current
       DESCRIPTION
           "The MAC address of the candidate."
       ::= {clusterCandidateEntry  1 }

clusterCandidateDesc OBJECT-TYPE
       SYNTAX     DisplayString (SIZE (0..42))
       MAX-ACCESS read-only
       STATUS     current
       DESCRIPTION
           "The description of the candidate."
       ::= {clusterCandidateEntry  3 }

clusterCandidateRole OBJECT-TYPE
       SYNTAX     INTEGER
                  {
                      candidate(2),
                      activeMember(3),
                      inactiveMember(4)
                  }
       MAX-ACCESS read-only
       STATUS     current
       DESCRIPTION
           "The role of the candidate.
                candidate(2)     : The switch is discovered by the commander,
                                   but it has not been manually configured for
                                   access from the commander.
                activeMember(3)  : The switch is manually configured for access
                                   from the commander and it is active in the
                                   cluster.
                inactiveMember(4): The switch is manually configured for access
                                   from the commander, but it is inactive in
                                   the cluster."
       ::= {clusterCandidateEntry  4 }

clusterMemberTable OBJECT-TYPE
    SYNTAX     SEQUENCE OF ClusterMemberEntry
    MAX-ACCESS not-accessible
    STATUS     current
    DESCRIPTION
        "A table listing clustering members."
    ::= { clusterMgt 10 }

clusterMemberEntry OBJECT-TYPE
    SYNTAX     ClusterMemberEntry
    MAX-ACCESS not-accessible
    STATUS     current
    DESCRIPTION
          "A conceptual row containing the information of the member."
    INDEX { clusterMemberId}
    ::= { clusterMemberTable 1 }

ClusterMemberEntry ::=
    SEQUENCE {
                clusterMemberId       Unsigned32,
                clusterMemberMacAddr  MacAddress,
                clusterMemberDesc     DisplayString,
                clusterMemberActive   INTEGER
             }

clusterMemberId OBJECT-TYPE
       SYNTAX     Unsigned32
       MAX-ACCESS not-accessible
       STATUS     current
       DESCRIPTION
           "The ID of the member."
       ::= {clusterMemberEntry  1 }

clusterMemberMacAddr OBJECT-TYPE
       SYNTAX     MacAddress
       MAX-ACCESS read-only
       STATUS     current
       DESCRIPTION
           "The MAC address of the member."
       ::= {clusterMemberEntry  2 }

clusterMemberDesc OBJECT-TYPE
       SYNTAX     DisplayString(SIZE (0..42))
       MAX-ACCESS read-only
       STATUS     current
       DESCRIPTION
           "The description of the member."
       ::= {clusterMemberEntry  3 }

clusterMemberActive OBJECT-TYPE
       SYNTAX     INTEGER
                  {
                      activeMember(3),
                      inactiveMember(4)
                  }
       MAX-ACCESS read-only
       STATUS     current
       DESCRIPTION
           "The active status of the member.
                activeMember(3)  : The switch is manually configured for access
                                   from the commander and it is active in the
                                   cluster.
                inactiveMember(4): The switch is manually configured for access
                                   from the commander, but it is inactive in
                                   the cluster."
       ::= {clusterMemberEntry  4 }

clusterMemberAddCtl  OBJECT IDENTIFIER ::= { clusterMgt 11 }

clusterMemberAddCtlMacAddr  OBJECT-TYPE
    SYNTAX     MacAddress
    MAX-ACCESS read-write
    STATUS     current
    DESCRIPTION
        "The MAC address of the device associated with clusterMemberAddCtlAction."
    ::= { clusterMemberAddCtl 1 }

clusterMemberAddCtlId  OBJECT-TYPE
    SYNTAX     Unsigned32
    MAX-ACCESS read-write
    STATUS     current
    DESCRIPTION
        "The member id associated with clusterMemberAddCtlAction."
    ::= { clusterMemberAddCtl 2 }

clusterMemberAddCtlAction  OBJECT-TYPE
    SYNTAX     INTEGER
               {
                   noAdd(1),
                   add(2)
               }
    MAX-ACCESS read-write
    STATUS     current
    DESCRIPTION
        "Adds the device to members that can be accessed from the commander.
         The MAC of the device is the current value of
         clusterMemberAddCtlMacAddr and the assigned member ID is the current
         value of clusterMemberAddCtlId. Set this object to add(2) to begin
         adding the member."
    ::= { clusterMemberAddCtl 5 }

clusterMemberRemoveCtl  OBJECT IDENTIFIER ::= { clusterMgt 12 }

clusterMemberRemoveCtlId  OBJECT-TYPE
    SYNTAX     Unsigned32
    MAX-ACCESS read-write
    STATUS     current
    DESCRIPTION
        "The member ID associated with clusterMemberRemoveCtlAction."
    ::= { clusterMemberRemoveCtl 1 }

clusterMemberRemoveCtlAction  OBJECT-TYPE
    SYNTAX     INTEGER
               {
                   noRemove(1),
                   remove(2)
               }
    MAX-ACCESS read-write
    STATUS     current
    DESCRIPTION
        "Removes the device from members that can be accessed from the commander.
         The member ID is the current value of clusterMemberRemoveCtlId.
         Set this object to remove(2) to begin removing the member."
    ::= { clusterMemberRemoveCtl 2 }

--
-- ipSrcGuardMgt ES3528MO-FLF-38-00149
--

ipSrcGuardConfigTable       OBJECT-TYPE
        SYNTAX      SEQUENCE OF IpSrcGuardConfigEntry
        MAX-ACCESS  not-accessible
        STATUS      current
        DESCRIPTION "A table contains the configurations to enable or disable
                     IP Source Guard at each port or trunk."
        ::= { ipSrcGuardMgt 1 }

ipSrcGuardConfigEntry       OBJECT-TYPE
        SYNTAX      IpSrcGuardConfigEntry
        MAX-ACCESS  not-accessible
        STATUS      current
        DESCRIPTION "An instance contains the configuration to enable
                     or disable IP Source Guard at each port or trunk."
        INDEX       { ipSrcGuardPortIfIndex }
        ::= { ipSrcGuardConfigTable 1 }

IpSrcGuardConfigEntry       ::= SEQUENCE
{
        ipSrcGuardPortIfIndex       InterfaceIndex,
        ipSrcGuardMode              INTEGER
}

ipSrcGuardPortIfIndex       OBJECT-TYPE
        SYNTAX      InterfaceIndex
        MAX-ACCESS  not-accessible
        STATUS      current
        DESCRIPTION "This object idents the port or trunk which is capable of
                     IP Source Guard feature."
        ::= { ipSrcGuardConfigEntry 1 }

ipSrcGuardMode      OBJECT-TYPE
        SYNTAX      INTEGER { diabled(0), srcIp(1), srcIpMac(2) }
        MAX-ACCESS  read-write
        STATUS      current
        DESCRIPTION "This object indicates whether Ip Source Guard is enabled
                     at this interface. If the value equals 0, it means Ip Source
                     Guard  is disabled. If the value equals 1, it means Ip Source
                     Guard is enabled, and packets are filtered by checking source ip.
                     If the value equals 2, it means Ip Source Guard is enabled
                     and packets are filtered by checking source ip and source mac."
        ::= { ipSrcGuardConfigEntry 2 }
--
ipSrcGuardAddrTable     OBJECT-TYPE
        SYNTAX      SEQUENCE OF IpSrcGuardAddrEntry
        MAX-ACCESS  not-accessible
        STATUS      current
        DESCRIPTION "A table contains the IP Source Guard bindings information
                     learnt by the device."
        ::= { ipSrcGuardMgt 2 }

ipSrcGuardAddrEntry     OBJECT-TYPE
        SYNTAX      IpSrcGuardAddrEntry
        MAX-ACCESS  not-accessible
        STATUS      current
        DESCRIPTION "An instance contains the Mac address, IP address type,
                     IP address, VLAN number, interface number, leased time and
                     status."
        INDEX   { ipSrcGuardBindingsVlanIndex, ipSrcGuardBindingsMacAddress }
        ::= { ipSrcGuardAddrTable 1 }

IpSrcGuardAddrEntry     ::= SEQUENCE
{
        ipSrcGuardBindingsVlanIndex         VlanIndex,
        ipSrcGuardBindingsMacAddress        MacAddress,
        ipSrcGuardBindingsAddrType          InetAddressType,
        ipSrcGuardBindingsEntryType         INTEGER,
        ipSrcGuardBindingsIpAddress         IpAddress,
        ipSrcGuardBindingsPortIfIndex       InterfaceIndex,
        ipSrcGuardBindingsLeaseTime         Unsigned32,
        ipSrcGuardBindingsStatus            RowStatus
}
ipSrcGuardBindingsVlanIndex      OBJECT-TYPE
        SYNTAX      VlanIndex
        MAX-ACCESS  not-accessible
        STATUS      current
        DESCRIPTION "This object indicates the VLAN which a DHCP client host
                     belongs to."
        ::= { ipSrcGuardAddrEntry 1 }

ipSrcGuardBindingsMacAddress     OBJECT-TYPE
        SYNTAX      MacAddress
        MAX-ACCESS  not-accessible
        STATUS      current
        DESCRIPTION "This object indicates the MAC address of a DHCP client
                     host."
        ::= { ipSrcGuardAddrEntry 2 }

ipSrcGuardBindingsAddrType       OBJECT-TYPE
        SYNTAX      InetAddressType
        MAX-ACCESS  read-create
        STATUS      current
        DESCRIPTION "This object indicates the type of IP address denoted in
                     ipSrcGuardBindingsIpAddress type."
        ::= { ipSrcGuardAddrEntry 3 }

ipSrcGuardBindingsEntryType     OBJECT-TYPE
        SYNTAX      INTEGER { dynamic(1), static(3) }
        MAX-ACCESS  read-only
        STATUS      current
        DESCRIPTION "This object indicates that this binding is obtained from
                     dynamically learning or is a static configuraion."
        ::= { ipSrcGuardAddrEntry 4 }

ipSrcGuardBindingsIpAddress     OBJECT-TYPE
        SYNTAX      IpAddress
        MAX-ACCESS  read-create
        STATUS      current
        DESCRIPTION "This object indicates the allocated IP address of
                     a DHCP client host."
        ::= { ipSrcGuardAddrEntry 5 }

ipSrcGuardBindingsPortIfIndex   OBJECT-TYPE
        SYNTAX      InterfaceIndex
        MAX-ACCESS  read-create
        STATUS      current
        DESCRIPTION "This object indicates the port or trunk where a DHCP client
                     host connects to."
        ::= { ipSrcGuardAddrEntry 6 }

ipSrcGuardBindingsLeaseTime     OBJECT-TYPE
        SYNTAX      Unsigned32
        MAX-ACCESS  read-only
        STATUS      current
        DESCRIPTION "This object indicates the leased time of this DHCP
                     bindings."
        ::= { ipSrcGuardAddrEntry 7 }

ipSrcGuardBindingsStatus     OBJECT-TYPE
        SYNTAX      RowStatus
        MAX-ACCESS  read-create
        STATUS      current
        DESCRIPTION "The status of this conceptual row entry. This object issued to
                     manage the creation and deletion of conceptual rows.
                     The status column has six defined values:  - 'active', which
                     indicates that the conceptual row is available for use by the
                     managed device;  - 'notInService', which indicates that the
                     conceptual row exists in the agent, but is unavailable for use
                     by the managed device."
        ::= { ipSrcGuardAddrEntry 8 }

--
-- upnpMgt
--

upnpStatus     OBJECT-TYPE
    SYNTAX      EnabledStatus
    MAX-ACCESS  read-write
    STATUS      current
    DESCRIPTION "Sets enabled(1) to enable UPnP device, and sets disabled(2) to
                 disable UPnP device."
    ::= { upnpMgt 1 }

upnpAdvertisingDuration     OBJECT-TYPE
    SYNTAX      Integer32 (60..86400)
    MAX-ACCESS  read-write
    STATUS      current
    DESCRIPTION "The interval(in seconds) between available UPnP device advertising
                 messages sent by the switch."
    ::= { upnpMgt 2 }

upnpTtl    OBJECT-TYPE
    SYNTAX      INTEGER (1..255)
    MAX-ACCESS  read-write
    STATUS      current
    DESCRIPTION "Specifies the TTL value of the UPnP advertising messages sent by
                 the switch. When the TTL value is greater than 1, it is possible
                 to send UPnP advertising messages to traverse multiple routers;
                 at the same time, the UPnP device will send an IGMP Join message
                 to the traverse multiple routers so that the routers will forward
                 multicast messages to the UPnP device."
    ::= { upnpMgt 3 }

--
-- trap definitions
--

es3626aTraps  OBJECT IDENTIFIER ::= { es3626aMIBNotifications 1 }
es3626aTrapsPrefix OBJECT IDENTIFIER ::= { es3626aTraps 0 }

swPowerStatusChangeTrap NOTIFICATION-TYPE
        OBJECTS     { swIndivPowerUnitIndex, swIndivPowerIndex, swIndivPowerStatus }
        STATUS      current
        DESCRIPTION "This trap is sent when the power state changes."
        ::= { es3626aTrapsPrefix 1 }

-- for Unicorn
swTemperatureOverHeatTrap NOTIFICATION-TYPE
        STATUS   current
        DESCRIPTION "This trap is sent when the temperature is too high."
        ::= { es3626aTrapsPrefix 2}

-- for FTTH
swInterfaceCardColdStartTrap NOTIFICATION-TYPE
        OBJECTS     { bladeIndex, bladeType, trapRestartType }
        STATUS      current
        DESCRIPTION "This trap is sent when the interface card performs a coldstart.
                     It can do so either through CLI/SNMP/WEB or interface card insert."
        ::= { es3626aTrapsPrefix 3 }

swUmcPowerDownTrap NOTIFICATION-TYPE
        OBJECTS     { bladeIndex, ifIndex }
        STATUS   current
        DESCRIPTION "This trap is sent when the Umc powers down"
        ::= { es3626aTrapsPrefix 4 }

swUmcPowerUpTrap NOTIFICATION-TYPE
        OBJECTS     { bladeIndex, ifIndex }
        STATUS   current
        DESCRIPTION "This trap is sent when the Umc powers up."
        ::= { es3626aTrapsPrefix 5 }

swLoopbackTestStartTrap NOTIFICATION-TYPE
        OBJECTS     { bladeIndex, ifIndex }
        STATUS   current
        DESCRIPTION "This trap is sent when the loopback test starts."
        ::= { es3626aTrapsPrefix 6 }

swLoopbackNotTestTrap NOTIFICATION-TYPE
        OBJECTS     { bladeIndex, ifIndex }
        STATUS   current
        DESCRIPTION "This trap is sent when the loopback not Test."
        ::= { es3626aTrapsPrefix 7}

swLoopbackOAMSettingTimeoutTrap NOTIFICATION-TYPE
        OBJECTS     { bladeIndex, ifIndex }
        STATUS   current
        DESCRIPTION "This trap is sent when the loopback OAM setting
                     timed out."
        ::= { es3626aTrapsPrefix 8 }

swLoopbackLBErrorTimeoutTrap NOTIFICATION-TYPE
        OBJECTS     { bladeIndex, ifIndex }
        STATUS   current
        DESCRIPTION "This trap is sent when the loopback LBError
                     has timed out."
        ::= { es3626aTrapsPrefix 9 }

swLoopbackOAMReleaseTimeoutTrap NOTIFICATION-TYPE
        OBJECTS     { bladeIndex, ifIndex }
        STATUS   current
        DESCRIPTION "This trap is sent when the loopback OAM release
                     has timed out."
        ::= { es3626aTrapsPrefix 10 }

swLoopbackNormalEndTrap NOTIFICATION-TYPE
        OBJECTS     { bladeIndex, ifIndex }
        STATUS   current
        DESCRIPTION "This trap is sent when the loopack ends normally."
        ::= { es3626aTrapsPrefix 11 }

swLoopbackBusyTrap NOTIFICATION-TYPE
        OBJECTS     { bladeIndex, ifIndex }
        STATUS   current
        DESCRIPTION "This trap is sent when the loopback test is busy."
        ::= { es3626aTrapsPrefix 12 }

swLoopbackStopTrap NOTIFICATION-TYPE
        OBJECTS     { bladeIndex, ifIndex }
        STATUS   current
        DESCRIPTION "This trap is sent when the loopback test has stopped."
        ::= { es3626aTrapsPrefix 13 }

swLoopbackUMCTimeoutTrap NOTIFICATION-TYPE
        OBJECTS     { bladeIndex, ifIndex }
        STATUS   current
        DESCRIPTION "This trap is sent when the loopback UMC has timed out."
        ::= { es3626aTrapsPrefix 14}

swDiagnosisStartTrap NOTIFICATION-TYPE
        OBJECTS     { bladeIndex, bladeType }
        STATUS   current
        DESCRIPTION "This trap is sent when the diagonosis has started."
        ::= { es3626aTrapsPrefix 15 }

swDiagnosisResultTrap NOTIFICATION-TYPE
        OBJECTS     { bladeIndex, bladeType, trapDiagnosisResult }
        STATUS   current
        DESCRIPTION "This trap is sent when the diagnosis has finished."
        ::= { es3626aTrapsPrefix 16 }

swFanFailureTrap NOTIFICATION-TYPE
        OBJECTS     { switchUnitIndex, switchFanIndex }
        STATUS   current
        DESCRIPTION "This trap is sent when the fan has failed."
        ::= { es3626aTrapsPrefix 17 }

swFanRecoverTrap NOTIFICATION-TYPE
        OBJECTS     { switchUnitIndex, switchFanIndex }
        STATUS   current
        DESCRIPTION "This trap is sent when fan failure has recovered."
        ::= { es3626aTrapsPrefix 18 }

swUmcLipFailureTrap NOTIFICATION-TYPE
        OBJECTS     { bladeIndex, ifIndex }
        STATUS   current
        DESCRIPTION "This trap is sent when the UMC optical has detected low input power."
        ::= { es3626aTrapsPrefix 19 }

swUmcLipRecoverTrap NOTIFICATION-TYPE
        OBJECTS     { bladeIndex, ifIndex }
        STATUS   current
        DESCRIPTION "This trap is sent when the UMC optical has recovered
                     from low input power."
        ::= { es3626aTrapsPrefix 20 }

swUmcLinkDownTrap NOTIFICATION-TYPE
        OBJECTS     { bladeIndex, ifIndex }
        STATUS   current
        DESCRIPTION "This trap is sent when the UMC UTP Port Link Down."
        ::= { es3626aTrapsPrefix 21 }

swUmcLinkUpTrap NOTIFICATION-TYPE
        OBJECTS     { bladeIndex, ifIndex }
        STATUS   current
        DESCRIPTION "This trap is sent when the UMC UTP Port Link Up."
        ::= { es3626aTrapsPrefix 22 }

swUmcMCFaultTrap NOTIFICATION-TYPE
        OBJECTS     { bladeIndex, ifIndex }
        STATUS   current
        DESCRIPTION "This trap is sent when the UMC media converter has a fault."
        ::= { es3626aTrapsPrefix 23 }

swUmcMCFaultRecoverTrap NOTIFICATION-TYPE
        OBJECTS     { bladeIndex, ifIndex }
        STATUS   current
        DESCRIPTION "This trap is sent when the UMC media converter
                     fault has recovered."
        ::= { es3626aTrapsPrefix 24 }

swLinkDownTrap NOTIFICATION-TYPE
        OBJECTS     { bladeIndex, ifIndex }
        STATUS   current
        DESCRIPTION "This trap is sent when the Port link Down."
        ::= { es3626aTrapsPrefix 25 }

swLinkUpTrap NOTIFICATION-TYPE
        OBJECTS     { bladeIndex, ifIndex }
        STATUS   current
        DESCRIPTION "This trap is sent when the Port link Up."
        ::= { es3626aTrapsPrefix 26 }

swHardwareFaultTrap NOTIFICATION-TYPE
        OBJECTS     { bladeIndex, bladeType }
        STATUS   current
        DESCRIPTION "This trap is sent when the interface card has a fault."
        ::= { es3626aTrapsPrefix 27 }

swHardwareFaultRecoverTrap NOTIFICATION-TYPE
        OBJECTS     { bladeIndex, bladeType }
        STATUS   current
        DESCRIPTION "This trap is sent when the interface card fault
                     has recovered."
        ::= { es3626aTrapsPrefix 28 }

swLinkChangeEventTrap NOTIFICATION-TYPE
        OBJECTS     { bladeIndex, ifIndex, trapSensitivityEventType }
        STATUS   current
        DESCRIPTION "This trap is sent when a Port Link change alarm
                     sensitivity event has occurred."
        ::= { es3626aTrapsPrefix 29 }

swUmcUtpLinkEventTrap NOTIFICATION-TYPE
        OBJECTS     { bladeIndex, ifIndex, trapSensitivityEventType }
        STATUS   current
        DESCRIPTION "This trap is sent when a UMC UTP Port link change
                     alarm sensitivity event has occurred."
        ::= { es3626aTrapsPrefix 30 }

swUmcLipEventTrap NOTIFICATION-TYPE
        OBJECTS     { bladeIndex, ifIndex, trapSensitivityEventType }
        STATUS   current
        DESCRIPTION "This trap is sent when a UMC UTP Port low input
                     power alarm sensitivity event has occurred."
        ::= { es3626aTrapsPrefix 31 }

swUmcMCFaultEventTrap NOTIFICATION-TYPE
        OBJECTS     { bladeIndex, ifIndex, trapSensitivityEventType }
        STATUS   current
        DESCRIPTION "This trap is sent when a UMC media converter fault
                     alarm sensitivity event has occurred."
        ::= { es3626aTrapsPrefix 32 }

swFanEventTrap NOTIFICATION-TYPE
        OBJECTS     { switchFanIndex, trapSensitivityEventType }
        STATUS   current
        DESCRIPTION "This trap is sent when a fan alarm sensitivity
                     event has occurred."
        ::= { es3626aTrapsPrefix 33 }

swHardwareFaultEventTrap NOTIFICATION-TYPE
        OBJECTS     { bladeIndex, bladeType, trapSensitivityEventType }
        STATUS   current
        DESCRIPTION "This trap is sent when a interface card alarm
                     sensitivity event has occurred."
        ::= { es3626aTrapsPrefix 34 }
-- for Unicorn
swMacAddressTrap NOTIFICATION-TYPE
        OBJECTS     { amtrMacAddrRisingThreshold, amtrMacAddrFallingThreshold }
        STATUS current
        DESCRIPTION "This trap is sent when mac address table is over
                     the amtrMacAddrRisingThreshold. Note that once this trap has
                     been sent, the next trigger time for this trap is after the
                     MAC address entry is below the amtrMacAddrFallingThreshold,
                     and exceeds the rising threshold again."
        ::= { es3626aTrapsPrefix 35 }

swPortSecurityTrap NOTIFICATION-TYPE
        OBJECTS       { ifIndex }
        STATUS        current
        DESCRIPTION "This trap is sent when the port is being intruded. This trap
                     will only be sent when the portSecAction is set to trap(2) or
                     trapAndShutdown(4)."
        ::= { es3626aTrapsPrefix 36 }




-- for FTTH_ES3526s

swFefiFailureTrap NOTIFICATION-TYPE
        OBJECTS     { ifIndex }
        STATUS   current
        DESCRIPTION "This trap is sent when Far End Fault Indication (FEFI) occurs."
        ::= { es3626aTrapsPrefix 37 }

swFefiRecoverTrap NOTIFICATION-TYPE
        OBJECTS     { ifIndex }
        STATUS   current
        DESCRIPTION "This trap is sent when Far End Fault Indication (FEFI) has
                     recovered."
        ::= { es3626aTrapsPrefix 38 }

-- for darwin start

swLoopbackTestFailureTrap NOTIFICATION-TYPE
       OBJECTS     { switchLoopbackTestFailurePorts }
       STATUS   current
       DESCRIPTION "This trap is sent when the loopback test fails."
       ::= { es3626aTrapsPrefix 39 }
-- for darwin end

swIpFilterRejectTrap NOTIFICATION-TYPE
        OBJECTS     { trapIpFilterRejectMode, trapIpFilterRejectIp }
        STATUS   current
        DESCRIPTION "This trap is sent when an incorrect IP address is rejected by
                      the ipfilter."
        ::= { es3626aTrapsPrefix 40 }

swSmtpConnFailureTrap NOTIFICATION-TYPE
        OBJECTS     { smtpServerIp }
        STATUS   current
        DESCRIPTION "This trap is triggered if the SMTP system
                     cannot open a connection to the mail server successfully."
        ::= { es3626aTrapsPrefix 41 }

swSettingToAllInterfacesTrap NOTIFICATION-TYPE
        OBJECTS     { trapVarMibObjId }
        STATUS      current
        DESCRIPTION "This trap is issued when a MIB object defined on
                     a per-interface basis is being set, but because of a
                     system limitation, this set action is applied to all
                     interfaces."
        ::= { es3626aTrapsPrefix 42 }

--poe traps start
pethPsePortOnOffNotification NOTIFICATION-TYPE
        OBJECTS     { pethPsePortDetectionStatus }
        STATUS      current
        DESCRIPTION
                " This Notification indicates if a Pse Port is delivering power to the PD. This notification SHOULD be sent on
                   every status change except in searching mode."
        ::= { es3626aTrapsPrefix 43 }

pethPsePortPowerMaintenanceStatusNotification NOTIFICATION-TYPE
        OBJECTS     { pethPsePortPowerMaintenanceStatus  }
        STATUS      current
        DESCRIPTION
              " This Notification indicates a Port Change Status and
                    SHOULD be sent on every status change."
        ::= { es3626aTrapsPrefix 44 }


pethMainPowerUsageOnNotification NOTIFICATION-TYPE
        OBJECTS     { pethMainPseConsumptionPower  }
        STATUS      current
        DESCRIPTION
              " This Notification indicates PSE Threshold usage indication is
                   on; the power usage is above the threshold."
        ::= { es3626aTrapsPrefix 45 }

pethMainPowerUsageOffNotification NOTIFICATION-TYPE
        OBJECTS     { pethMainPseConsumptionPower }
        STATUS      current
        DESCRIPTION
              " This Notification indicates that the PSE Threshold usage indication
                 is off; the usage power is below the threshold."
        ::= { es3626aTrapsPrefix 46 }
--poe traps end

--hsrp trap start
cHsrpStateChange NOTIFICATION-TYPE
        OBJECTS { cHsrpGrpStandbyState }
        STATUS current
        DESCRIPTION
                    "A cHsrpStateChange notification is sent when a
                     cHsrpGrpStandbyState transitions to either active or
                     standby state, or leaves active or standby state. There
                     will be only one notification issued when the state change
                     is from standby to active and vice versa."
        ::= { es3626aTrapsPrefix 47 }

--hsrp trap end

--vdsl line trap start
vdslPerfLofsThreshNotification NOTIFICATION-TYPE
        OBJECTS      {
                     vdslPerfCurr15MinLofs
                     }
        STATUS       current
        DESCRIPTION
            "Loss of Framing 15-minute interval threshold
             (vdslThresh15MinLofs) reached."
        ::= { es3626aTrapsPrefix 48 }

vdslPerfLossThreshNotification NOTIFICATION-TYPE
        OBJECTS       {
                      vdslPerfCurr15MinLoss
                      }
        STATUS        current
        DESCRIPTION
            "Loss of Signal 15-minute interval threshold
            (vdslThresh15MinLoss) reached."
        ::= { es3626aTrapsPrefix 49 }

vdslPerfLprsThreshNotification NOTIFICATION-TYPE
        OBJECTS       {
                      vdslPerfCurr15MinLprs
                      }
        STATUS        current
        DESCRIPTION
            "Loss of Power 15-minute interval threshold
            (vdslThresh15MinLprs) reached."
        ::= { es3626aTrapsPrefix 50 }

vdslPerfLolsThreshNotification NOTIFICATION-TYPE
        OBJECTS       {
                      vdslPerfCurr15MinLols
                      }
        STATUS        current
        DESCRIPTION
            "Loss of Link 15-minute interval threshold
            (vdslThresh15MinLols) reached."
        ::= { es3626aTrapsPrefix 51 }

vdslPerfESsThreshNotification NOTIFICATION-TYPE
        OBJECTS       {
                      vdslPerfCurr15MinESs
                      }
        STATUS        current
        DESCRIPTION
            "Errored Seconds 15-minute interval threshold
            (vdslThresh15MinESs) reached."
        ::= { es3626aTrapsPrefix 52 }

vdslPerfSESsThreshNotification NOTIFICATION-TYPE
        OBJECTS       {
                      vdslPerfCurr15MinSESs
                      }
        STATUS        current
        DESCRIPTION
            "Severely Errored Seconds 15-minute interval threshold
            (vdslThresh15MinSESs) reached."
        ::= { es3626aTrapsPrefix 53 }

vdslPerfUASsThreshNotification NOTIFICATION-TYPE
        OBJECTS       {
                      vdslPerfCurr15MinUASs
                      }
        STATUS        current
        DESCRIPTION
            "Unavailable Seconds 15-minute interval threshold
            (vdslThresh15MinUASs) reached."
        ::= { es3626aTrapsPrefix 54 }

--vdsl line trap end

swMaxMacCountTrap NOTIFICATION-TYPE
        OBJECTS       { portSecMaxMacCount }
        STATUS        current
        DESCRIPTION
            "This trap is sent when the port security maximum MAC
             address number count is exceeded."
        ::= { es3626aTrapsPrefix 55 }

swMainBoardVerMismatchNotificaiton NOTIFICATION-TYPE
        OBJECTS       { swOpCodeVer, swOpCodeVer}
        STATUS        current
        DESCRIPTION
            "This trap is sent when the slave version is mismatch with the
             master version. This trap will binds two object, the first object
             indicate the master version, whereas the second represent the
             slave version. "
        ::= { es3626aTrapsPrefix 56 }

swModuleVerMismatchNotificaiton NOTIFICATION-TYPE
        OBJECTS  { swExpectedModuleOpCodeVer, swModuleOpCodeVer }
        STATUS        current
        DESCRIPTION
              "This trap is sent when the module version is mismatch with the
               main board version. "
        ::= { es3626aTrapsPrefix 57 }

swThermalRisingNotification NOTIFICATION-TYPE
        OBJECTS  { switchThermalTempValue, switchThermalActionRisingThreshold }
        STATUS   current
        DESCRIPTION
             "This trap is sent when the temperature is over the
             switchThermalActionRisingThreshold."
        ::= { es3626aTrapsPrefix 58 }

swThermalFallingNotification NOTIFICATION-TYPE
        OBJECTS  { switchThermalTempValue, switchThermalActionFallingThreshold }
        STATUS   current
        DESCRIPTION
             "This trap is sent when the temperature is below the
             switchThermalActionFallingThreshold."
        ::= { es3626aTrapsPrefix 59 }

swModuleInsertionNotificaiton NOTIFICATION-TYPE
        OBJECTS       { swModuleOpCodeVer}
        STATUS        current
        DESCRIPTION
            "This trap is sent when the module is inserted."
        ::= { es3626aTrapsPrefix 60 }

swModuleRemovalNotificaiton NOTIFICATION-TYPE
        OBJECTS  { swModuleOpCodeVer }
        STATUS        current
        DESCRIPTION
              "This trap is sent when the module is removed."
        ::= { es3626aTrapsPrefix 61 }

--amap trap

amapStatusTrap NOTIFICATION-TYPE
        OBJECTS  { amapLastTrapReason, amapLastTrapPort }
        STATUS        current
        DESCRIPTION
              "An AMAP port status change and reason."
        ::= { es3626aTrapsPrefix 62 }

tcnTrap NOTIFICATION-TYPE
        OBJECTS  { trapVarTcnReason }
        STATUS        current
        DESCRIPTION
              "The variable represents the function of TCN:
                     pushButton(1): Enables the unit as the Master unit in the stack.
                     stackingLinkDown(2): Master stacking link is down.
                     stackingLinkUp(3): Master stacking link is up.
                     hbtTimeout(4): Control packet sent from the Master through all units has timed-out.
                     hbtError(5): Control packet sent from the Master through all units was received with errors.
                     slave(6): A Slave unit notifies the Master unit of a topology change."
        ::= { es3626aTrapsPrefix 63 }

swIpForwardingChangedByMstpTrap NOTIFICATION-TYPE
        STATUS      current
        DESCRIPTION
              "This trap is sent when Layer 3 IP Routing Status changes
                     because the user enables or disables 802.1s (Multiple Spanning
                     Tree). Layer 3 routing in the chip is disabled when
                     spanning tree protocol is running with 802.1s (Multiple Spanning Tree)
                     protocol. That is, ingress packets will not be routed across
                     VLAN boundaries. Layer 3 routing protocol status should also be
                     disabled in this scenario."
        ::= { es3626aTrapsPrefix 64 }

swStartupConfigChangedTrap NOTIFICATION-TYPE
        OBJECTS     { trapVarLoginUserName, trapVarLoginMethod, trapVarLoginTime  }
        STATUS   current
        DESCRIPTION "This trap will be triggered if the startup configuration is changed."
        ::= { es3626aTrapsPrefix 65 }

swAuthenticationFailure NOTIFICATION-TYPE
        OBJECTS     { trapVarLoginUserName, trapVarLoginMethod, trapVarLoginIPAddress, trapVarLoginTime }
        STATUS   current
        DESCRIPTION "This trap will be triggered if authentication is fails."
        ::= { es3626aTrapsPrefix 66 }

swAuthenticationSuccess NOTIFICATION-TYPE
        OBJECTS     { trapVarLoginUserName, trapVarLoginMethod, trapVarLoginIPAddress, trapVarLoginTime }
        STATUS   current
        DESCRIPTION "This trap will be triggered if authentication is successful."
        ::= { es3626aTrapsPrefix 67 }

swAuthenticationFailureWithInetAddress NOTIFICATION-TYPE
        OBJECTS     { trapVarLoginUserName, trapVarLoginMethod, trapVarLoginInetAddressType, trapVarLoginInetAddress }
        STATUS   current
        DESCRIPTION "This trap will be triggered if authentication is fail."
        ::= { es3626aTrapsPrefix 68 }
swAuthenticationSuccessWithInetAddress NOTIFICATION-TYPE
        OBJECTS     { trapVarLoginUserName, trapVarLoginMethod, trapVarLoginInetAddressType, trapVarLoginInetAddress }
        STATUS   current
        DESCRIPTION "This trap will be triggered if authentication is successful."
        ::= { es3626aTrapsPrefix 69 }

--
-- ATC trap ASE3528B-E1-FLF-P5-00011
--
swAtcBcastStormAlarmFireTrap NOTIFICATION-TYPE
        OBJECTS     {
                        atcBcastStormIfIndex,
                        atcBcastStormSampleType,
                        atcBcastStormCurrentTrafficRate,
                        atcBcastStormAlarmFireThreshold
                    }
        STATUS      current
        DESCRIPTION
            "When the broadcast traffic is detected as the storm, this trap
             will be fired."
        ::= { es3626aTrapsPrefix 70 }

swAtcBcastStormAlarmClearTrap NOTIFICATION-TYPE
        OBJECTS     {
                        atcBcastStormIfIndex,
                        atcBcastStormSampleType,
                        atcBcastStormCurrentTrafficRate,
                        atcBcastStormAlarmClearThreshold
                    }
        STATUS      current
        DESCRIPTION
            "When the broadcast storm is detected as the normal traffic, this
             trap will be fired."
        ::= { es3626aTrapsPrefix 71 }

swAtcBcastStormTcApplyTrap NOTIFICATION-TYPE
        OBJECTS     {
                        atcBcastStormIfIndex,
                        atcBcastStormSampleType,
                        atcBcastStormCurrentTrafficRate,
                        atcBcastStormAlarmFireThreshold,
                        atcBcastStormTcApplyTime
                    }
        STATUS      current
        DESCRIPTION
            "When the ATC is activated, this trap will be fired."
        ::= { es3626aTrapsPrefix 72 }

swAtcBcastStormTcReleaseTrap NOTIFICATION-TYPE
        OBJECTS     {
                        atcBcastStormIfIndex,
                        atcBcastStormSampleType,
                        atcBcastStormCurrentTrafficRate,
                        atcBcastStormAlarmClearThreshold,
                        atcBcastStormTcReleaseTime
                    }
        STATUS      current
        DESCRIPTION
            "When the ATC is released, this trap will be fired."
        ::= { es3626aTrapsPrefix 73 }

swAtcMcastStormAlarmFireTrap      NOTIFICATION-TYPE
        OBJECTS     {
                        atcMcastStormIfIndex,
                        atcMcastStormSampleType,
                        atcMcastStormCurrentTrafficRate,
                        atcMcastStormAlarmFireThreshold
                    }
        STATUS      current
        DESCRIPTION
            "When the multicast traffic is detected as the storm, this trap
             will be fired."
        ::= { es3626aTrapsPrefix 74 }

swAtcMcastStormAlarmClearTrap NOTIFICATION-TYPE
        OBJECTS     {
                        atcMcastStormIfIndex,
                        atcMcastStormSampleType,
                        atcMcastStormCurrentTrafficRate,
                        atcMcastStormAlarmClearThreshold
                    }
        STATUS      current
        DESCRIPTION
            "When the multicast storm is detected as the normal traffic, this
             trap will be fired."
        ::= { es3626aTrapsPrefix 75 }

swAtcMcastStormTcApplyTrap NOTIFICATION-TYPE
        OBJECTS     {
                        atcMcastStormIfIndex,
                        atcMcastStormSampleType,
                        atcMcastStormCurrentTrafficRate,
                        atcMcastStormAlarmFireThreshold,
                        atcMcastStormTcApplyTime
                    }
        STATUS      current
        DESCRIPTION
            "When the ATC is activated, this trap will be fired."
        ::= { es3626aTrapsPrefix 76 }

swAtcMcastStormTcReleaseTrap NOTIFICATION-TYPE
        OBJECTS     {
                        atcMcastStormIfIndex,
                        atcMcastStormSampleType,
                        atcMcastStormCurrentTrafficRate,
                        atcMcastStormAlarmClearThreshold,
                        atcMcastStormTcReleaseTime
                    }
        STATUS      current
        DESCRIPTION
            "When the ATC is released, this trap will be fired."
        ::= { es3626aTrapsPrefix 77 }

--
-- Major/Minor Alarm ASE3528B-E1-FLF-P5-00004
--
swMajorAlarm    NOTIFICATION-TYPE
        OBJECTS     { alarmMajorType }
        STATUS      current
        DESCRIPTION
            "This trap is fired when the major alarm event occured."
        ::= { es3626aTrapsPrefix 78 }

swMinorAlarm    NOTIFICATION-TYPE
        OBJECTS     { alarmMinorType }
        STATUS      current
        DESCRIPTION
            "This trap is fired when the minor alarm event occured."
        ::= { es3626aTrapsPrefix 79 }
--
-- ASE3528B-E1-FLF-P5
--

swPowerUnitUnmount  NOTIFICATION-TYPE
    OBJECTS     { swIndivPowerUnitIndex, swIndivPowerIndex }
    STATUS      current
    DESCRIPTION "This trap will be fired when the power module is unplugged."
    ::= { es3626aTrapsPrefix 80 }

swPowerSourceOn     NOTIFICATION-TYPE
    OBJECTS     { swIndivPowerUnitIndex, swIndivPowerIndex }
    STATUS      current
    DESCRIPTION "This trap will be fired when the power source is available."
    ::= { es3626aTrapsPrefix 81 }

swPowerSourceOff    NOTIFICATION-TYPE
    OBJECTS     { swIndivPowerUnitIndex, swIndivPowerIndex }
    STATUS      current
    DESCRIPTION "This trap will be fired when the power source is unavailable."
    ::= { es3626aTrapsPrefix 82 }

swThermalRisingRecoveryNotification NOTIFICATION-TYPE
    OBJECTS  { switchThermalTempValue, switchThermalActionRisingThreshold }
    STATUS   current
    DESCRIPTION
         "This trap is sent when the temperature was returned to normal."
     ::= { es3626aTrapsPrefix 83 }

swSfpModuleInsertionFailed    NOTIFICATION-TYPE
    OBJECTS      { ifIndex }
    STATUS       current
    DESCRIPTION  "This trap is fired when the SFP module cannot be identified."
    ::= { es3626aTrapsPrefix  84 }

swEqpAlarmRecovery    NOTIFICATION-TYPE
    OBJECTS     { alarmEqpRecoveryType }
    STATUS      current
    DESCRIPTION "This trap is fired when the EQP alarm recovery event occured."
    ::= { es3626aTrapsPrefix 85 }

-- [Terawave]

swAlarmInput    NOTIFICATION-TYPE
    OBJECTS     { alarmInputType }
    STATUS      current
    DESCRIPTION "This trap is fired when the alarm input event occurs."
    ::= { es3626aTrapsPrefix 90 }

-- [Juniper]

stpBpduGuardPortShutdownTrap    NOTIFICATION-TYPE
    OBJECTS     { ifIndex }
    STATUS      current
    DESCRIPTION "This trap is sent when the port has been shut down resulting from
                 receiving BPDU. Both BPDU guard and oper edge port are enabled
                 on the port."
    ::= { es3626aTrapsPrefix 91 }

-- conformance information

es3626aMIBCompliances OBJECT IDENTIFIER   ::= { es3626aMIBConformance 1 }
es3626aMIBGroups      OBJECT IDENTIFIER   ::= { es3626aMIBConformance 2 }

es3626aMIBCompliances1 MODULE-COMPLIANCE
    STATUS  current
    DESCRIPTION
            "The compliance statement for entities which implement
             Mercury PlatForm Priavte MIB for Accton."
    MODULE  -- this module

        GROUP        switchMgtGroup
        DESCRIPTION  "This group is mandatory for implementations
                     of the switchMgt capability."

        GROUP        portMgtGroup
        DESCRIPTION  "This group is mandatory for implementations
                     of the portMgt capability."

        GROUP        trunkMgtGroup
        DESCRIPTION  "This group is mandatory for implementations
                     of the trunkMgt capability."

        GROUP        lacpMgtGroup
        DESCRIPTION  "This group is mandatory for implementations
                     of the lacpMgt capability."

        GROUP        staMgtGroup
        DESCRIPTION  "This group is mandatory for implementations
                     of the staMgt capability."

        GROUP        tftpMgtGroup
        DESCRIPTION  "This group is mandatory for implementations
                     of the tftpMgt capability."

        GROUP        restartMgtGroup
        DESCRIPTION  "This group is mandatory for implementations
                     of the restartMgt capability."

        GROUP        mirrorMgtGroup
        DESCRIPTION  "This group is mandatory for implementations
                     of the mirrorMgt capability."

        GROUP        igmpSnoopMgtGroup
        DESCRIPTION  "This group is mandatory for implementations
                     of the igmpSnoopMgt capability."

        GROUP        ipMgtGroup
        DESCRIPTION  "This group is mandatory for implementations
                     of the ipMgt capability."

        GROUP        bcastStormMgtGroup
        DESCRIPTION  "This group is mandatory for implementations
                     of the bcastStormMgt capability."

        GROUP        vlanMgtGroup
        DESCRIPTION  "This group is mandatory for implementations
                     of the vlanMgt capability."

        GROUP        priorityMgtGroup
        DESCRIPTION  "This group is mandatory for implementations
                     of the priorityMgt capability."

        GROUP        trapDestMgtGroup
        DESCRIPTION  "This group is mandatory for implementations
                     of the trapDestMgt capability."

        GROUP        vdslMgtGroup
        DESCRIPTION  "This group is mandatory for implementations
                     of the vdslMgt capability."

        GROUP        qosMgtGroup
        DESCRIPTION  "This group is mandatory for implementations
                     of the qosMgt capability."

        GROUP        securityMgtGroup
        DESCRIPTION  "This group is mandatory for implementations
                     of the qosMgt capability."

        GROUP        layer3MgtGroup
        DESCRIPTION  "This group is mandatory for implementations
                     of the layer3Mgt capability."

        GROUP        sysLogMgtGroup
        DESCRIPTION  "This group is mandatory for implementations
                     of the sysLogMgt capability."

        GROUP        lineMgtGroup
        DESCRIPTION  "This group is mandatory for implementations
                     of the lineMgt capability."

        GROUP        bladeMgtGroup
        DESCRIPTION  "This group is mandatory for implementations
                     of the bladeMgt capability."

        GROUP        ftthMgtGroup
        DESCRIPTION  "This group is mandatory for implementations
                     of the ftthMgt capability."

    ::= { es3626aMIBCompliances 1 }

-- units of conformance

switchMgtGroup OBJECT-GROUP
    OBJECTS { switchManagementVlan, switchNumber, swHardwareVer,
              swMicrocodeVer, swLoaderVer, swBootRomVer, swOpCodeVer,
              swPortNumber, swPowerStatus, swRoleInSystem, swSerialNumber,
              swExpansionSlot1, swExpansionSlot2, swServiceTag,
              switchOperState, swProdName, swProdManufacturer,
              swProdDescription, swProdVersion, swProdUrl, swIdentifier,
              swChassisServiceTag, swIndivPowerUnitIndex,
              swIndivPowerIndex, swIndivPowerStatus, switchJumboFrameStatus,
              amtrMacAddrRisingThreshold, amtrMacAddrFallingThreshold
               }
    STATUS  current
    DESCRIPTION
            "A collection of objects for managing the switch system,
             or individual units in a stackable switch system.
             For a nonstackable system, only unit 1 exists."
    ::= { es3626aMIBGroups 1 }

portMgtGroup OBJECT-GROUP
    OBJECTS { portName, portType, portSpeedDpxCfg, portFlowCtrlCfg,
              portCapabilities, portAutonegotiation, portSpeedDpxStatus,
              portFlowCtrlStatus, portTrunkIndex, portEthernetType,
              portLoopBackTestAction, portLoopBackTestResult
              }
    STATUS  current
    DESCRIPTION
            "A collection of objects for Management ports.
             This group also provides information related to trunks
             since they share the same properties."
    ::= { es3626aMIBGroups 2 }


trunkMgtGroup OBJECT-GROUP
    OBJECTS { trunkMaxId, trunkValidNumber, trunkPorts, trunkCreation,
              trunkStatus, trunkGroup }
    STATUS  current
    DESCRIPTION
            "A collection of objects to provide additional information
             for Trunks,"
    ::= { es3626aMIBGroups 3 }

lacpMgtGroup OBJECT-GROUP
    OBJECTS { lacpPortStatus }
    STATUS        current
    DESCRIPTION
            "A collection of objects for Managing  Link Aggregation
             Control Protocol (LACP, 802.3ad), that is dynamic trunking."
    ::= { es3626aMIBGroups 4 }

staMgtGroup OBJECT-GROUP
    OBJECTS { staSystemStatus, staPortFastForward, staPortProtocolMigration,
              staPortAdminEdgePort, staPortOperEdgePort, staPortAdminPointToPoint,
              staPortOperPointToPoint, staPortLongPathCost, staProtocolType,
              staTxHoldCount, staPathCostMethod, mstName, mstRevision, mstMaxHops,
              mstInstanceEditVlansMap, mstInstanceEditVlansMap2k,
              mstInstanceEditVlansMap3k, mstInstanceEditVlansMap4k,
              xstInstanceCfgPriority, xstInstanceCfgTimeSinceTopologyChange,
              xstInstanceCfgTopChanges, xstInstanceCfgDesignatedRoot,
              xstInstanceCfgRootCost, xstInstanceCfgRootPort,
              xstInstanceCfgMaxAge, xstInstanceCfgHelloTime, xstInstanceCfgHoldTime,
              xstInstanceCfgForwardDelay, xstInstanceCfgBridgeMaxAge,
              xstInstanceCfgBridgeHelloTime, xstInstanceCfgBridgeForwardDelay,
              xstInstanceCfgTxHoldCount, xstInstanceCfgPathCostMethod,
              xstInstancePortPriority, xstInstancePortState, xstInstancePortEnable,
              xstInstancePortPathCost, xstInstancePortDesignatedRoot,
              xstInstancePortDesignatedCost, xstInstancePortDesignatedBridge,
              xstInstancePortDesignatedPort, xstInstancePortForwardTransitions,
              xstInstancePortPortRole
            }
    STATUS  current
    DESCRIPTION
            "A collection of objects for managing Spanning Tree Algorithm
            (STA). This has variables not already defined in the implemented
            standard MIB(s)."
    ::= { es3626aMIBGroups 5 }

tftpMgtGroup OBJECT-GROUP
    OBJECTS { tftpFileType, tftpSrcFile, tftpDestFile, tftpServer,
              tftpAction, tftpStatus
            }
    STATUS  current
    DESCRIPTION
            "A collection of objects for managing Trivial File Transfer
             Protocol (TFTP). This is responsible for file upload to a
             server and download from a server. Supports root guard
             capabilities."
    ::= { es3626aMIBGroups 6 }

restartMgtGroup OBJECT-GROUP
    OBJECTS      {
                    restartOpCodeFile, restartConfigFile, restartControl,
                    restartResetBlade, restartResetBladePort
                  }
    STATUS        current
    DESCRIPTION
            "A collection of objects for handling the restart capabilities
             of the switch,"
    ::= { es3626aMIBGroups 7 }

mirrorMgtGroup OBJECT-GROUP
    OBJECTS {  mirrorType, mirrorStatus}
    STATUS  current
    DESCRIPTION
            "A collection of objects for managing port mirroring."
    ::= { es3626aMIBGroups 8 }

igmpSnoopMgtGroup OBJECT-GROUP
    OBJECTS {
              igmpSnoopStatus, igmpSnoopQuerier, igmpSnoopQueryCount,
              igmpSnoopQueryInterval, igmpSnoopQueryMaxResponseTime,
              igmpSnoopRouterPortExpireTime, igmpSnoopVersion,
              igmpSnoopRouterCurrentPorts, igmpSnoopRouterCurrentStatus,
              igmpSnoopRouterStaticPorts, igmpSnoopRouterStaticStatus,
              igmpSnoopMulticastCurrentPorts,
              igmpSnoopMulticastCurrentStatus,
              igmpSnoopMulticastStaticPorts, igmpSnoopMulticastStaticStatus
            }
    STATUS  current
    DESCRIPTION
        "Objects for managing Internet Group Management Protocol (IGMP) snooping."
    ::= { es3626aMIBGroups 9 }

ipMgtGroup OBJECT-GROUP
    OBJECTS {
              netConfigPrimaryInterface, netConfigUnnumbered, netConfigStatus,
              netDefaultGateway, ipHttpState, ipHttpPort, ipDhcpRestart,
              ipHttpsState, ipHttpsPort, ipIcmpRedirectStatus, ipIrdpProcessStatus,
              ipIrdpAdvertisementAddress, ipIrdpMaxAdvertisementInterval,
              ipIrdpMinAdvertisementInterval, ipIrdpAdvertisementLifetime,
              ipIrdpPreferenceLevel, nifInterfaceAddressMethod, dhcpcIfClientIdMode,
              dhcpcIfClientId, dhcpRelayIfStatus
               }
    STATUS  current
    DESCRIPTION
        "Objects for managing Internet Protocol (IP)."
    ::= { es3626aMIBGroups 10 }

bcastStormMgtGroup OBJECT-GROUP
    OBJECTS { bcastStormStatus, bcastStormSampleType, bcastStormPktRate,
              bcastStormOctetRate, bcastStormPercent
            }
    STATUS  current
    DESCRIPTION
        "Objects for managing Broadcast Storm Control."
    ::= { es3626aMIBGroups 11 }

vlanMgtGroup OBJECT-GROUP
    OBJECTS {   vlanAddressMethod, vlanPortMode, vlanPortPrivateVlanType }
    STATUS  current
    DESCRIPTION
            "Objects for managing Virtual Local Area Networks (VLAN)."

    ::= { es3626aMIBGroups 12 }

priorityMgtGroup OBJECT-GROUP
     OBJECTS {
                prioIpPrecDscpStatus, prioIpPrecCos, prioIpPrecRestoreDefault,
                prioIpDscpCos, prioIpDscpRestoreDefault, prioIpPortEnableStatus,
                prioIpPortCos, prioIpPortStatus, prioCopyIpPrec, prioCopyIpDscp,
                prioCopyIpPort, prioWrrWeight, prioQueueMode
             }
     STATUS  current
     DESCRIPTION
              "A collection of objects managing traffic priority. They allow
              a user to specify which data packets have greater precedence when
              traffic is buffered in the switch due to congestion."
     ::= { es3626aMIBGroups 13 }

trapDestMgtGroup OBJECT-GROUP
     OBJECTS {
                trapDestCommunity, trapDestStatus, trapDestVersion, trapRestartType,
                trapSensitivityEventType, trapDiagnosisResult, switchFanIndex,
                trapEnableAll, trapBladeEnableStatus, trapEnablePortStatus,
                trapEnableAllAlarm, trapEnableAlarmSensitivity
             }
     STATUS  current
     DESCRIPTION
             "A collection of objects managing the SNMP traps and trap destinations."
     ::= { es3626aMIBGroups 14 }

vdslMgtGroup OBJECT-GROUP
    OBJECTS {
              vdslPortActive, vdslPortRDL, vdslPortProfile, vdslGenStatusLink,
              vdslGenStatusFailCnt, vdslPMDStatusSNR, vdslPMDStatusDSRate,
              vdslPMDStatusUSRate, vdslPMDStatusLocalPwr, vdslPMDStatusRemotePwr,
              vdslPMSTCStatusDSRSErr, vdslPMSTCStatusUSRSErr, vdslPMSTCStatusLocalMRX,
              vdslPMSTCStatusRemoteMRX, vdslPortUserProfileDownlink,
              vdslPortUserProfileUplink, vdslPortUserProfileInterleave
            }
    STATUS  current
    DESCRIPTION
            "A collection of objects for managing Very high data rate Digital
             Subscriber Line (VDSL)."
    ::= { es3626aMIBGroups 15 }

qosMgtGroup OBJECT-GROUP
         OBJECTS {
                    rateLimitStatus, rlPortInputLimit, rlPortOutputLimit,
                    rlPortInputLimitPercent, rlPortOutputLimitPercent,
                    rlPortInputStatus, rlPortOutputStatus
                    }
    STATUS        current
    DESCRIPTION
            "A collection of objects for managing Quality of Service (QoS) for
             network traffic."
    ::= { es3626aMIBGroups 16 }

securityMgtGroup OBJECT-GROUP
    OBJECTS      {
                    privateVlanStatus, privateVlanUplinkPorts, privateVlanDownlinkPorts,
                    privateVlanVlanType, privateVlanAssoicatedPrimaryVlan,
                    privateVlanPrivatePortSecondaryVlan,
                    privateVlanPromPortPrimaryVlanId,
                    privateVlanPromPortSecondaryRemap,
                    privateVlanPromPortSecondaryRemap2k,
                    privateVlanPromPortSecondaryRemap3k,
                    privateVlanPromPortSecondaryRemap4k,
                    portSecPortStatus, portSecAction,
                    pfuRuleAction, pfuRuleProtocol, pfuRuleSrcIpAddr,
                    pfuRuleSrcIpBitmask, pfuRuleSrcPortRange1, pfuRuleSrcPortRange2,
                    pfuRuleDstIpAddr, pfuRuleDstIpBitmask, pfuRuleDstPortRange1,
                    pfuRuleDstPortRange2, pfuRuleTcpCode, pfuRuleTcpCodeBitmask,
                    pfuRuleFragments, pfuRuleLog, pfuRuleRowStatus, pfuNextAvailable,
                    pfuInsert, radiusServerAddress, radiusServerPortNumber,
                    radiusServerKey, radiusServerRetransmit, radiusServerTimeout,
                    tacacsServerAddress, tacacsServerPortNumber, tacacsServerKey,
                    sshServerStatus, sshServerMajorVersion, sshServerMinorVersion,
                    sshTimeout, sshAuthRetries,  sshConnMajorVersion, sshConnMinorVersion,
                    sshConnStatus, sshConnEncryptionType, sshConnUserName,
                    sshDisconnect
                   }
    STATUS        current
    DESCRIPTION
            "A collection of objects for managing security, e.g., user security and
            port security."
    ::= { es3626aMIBGroups 17 }

layer3MgtGroup OBJECT-GROUP
    OBJECTS { arpCacheDeleteAll, arpCacheTimeout,  arpProxyArpStatus,
              ripUpdateTime, ripTimeoutTime, ripGarbageCollectionTime,
              ripRoutingProcessStatus, ripRouterVersion, ripSplitHorizonStatus,
              ripStatisticsReset, ospfRouterIdType, ospfRfc1583CompatibleState,
              ospfAutoCost, ospfOriginateDefaultRoute, ospfAdvertiseDefaultRoute,
              ospfExternalMetricType, ospfDefaultExternalMetric,
              ospfSpfHoldTime, ospfSpfDelayTime, ospfAreaNumber,
              ospfNssaRedistributeStatus, ospfNssaOriginateDefaultInfoStatus,
              ospfNssaStatus, ospfRedistributeMetricType, ospfRedistributeMetric,
              ospfRedistributeStatus, ospfSummaryStatus, ospfNetworkAreaAreaId,
              ospfNetworkAreaStatus
             }
    STATUS  current
    DESCRIPTION
            "A collection of objects for managing layer 3 settings and protocols."
    ::= { es3626aMIBGroups 18 }

sysLogMgtGroup OBJECT-GROUP
    OBJECTS { sysLogStatus, sysLogHistoryFlashLevel, sysLogHistoryRamLevel,
              sysLogLoggingInterval, sysLogLoggingCount, remoteLogStatus,
              remoteLogLevel, remoteLogFacilityType, remoteLogServerStatus}
    STATUS  current
    DESCRIPTION
            "Objects for managing the system log. This configures the logging
             of events by the switch"
    ::= { es3626aMIBGroups 19 }

lineMgtGroup OBJECT-GROUP
    OBJECTS {
              consoleDataBits, consoleParity, consoleBaudRate, consoleStopBits,
              consoleExecTimeout, consolePasswordThreshold, telnetExecTimeout,
              telnetPasswordThreshold
            }
    STATUS  current
    DESCRIPTION
            "A collection of objects for line management. This includes management
             for the serial line (RS232 port) and for Telnet."
    ::= { es3626aMIBGroups 20 }

bladeMgtGroup OBJECT-GROUP
    OBJECTS {
              bladeIndex, bladeType, bladeCopyFileName, bladeCopyDestBlade,
              bladeCopyAction, bladeCopyStatus, bladeCopySuccessList,
              bladeCopyFailureList
            }
    STATUS  current
    DESCRIPTION
            "A collection of objects for managing blades in a multiblade system.
             Each blade is an individual switch."
    ::= { es3626aMIBGroups 21 }

ftthMgtGroup OBJECT-GROUP
    OBJECTS {
              ftthUmcPowerStatus, ftthLipFefiStatus, ftthMCFaultStatus,
              ftthUmcLinkStatus, ftthLoopBackStatus, ftthUtpPortLinkSpeed,
              ftthUtpPortDuplexMode, ftthUtpPortLinkNegotiation,
              ftthVendorCode, ftthVendorModelNumber,
              ftthTrapEnableInterfaceCardColdStart, ftthTrapEnableUmcPowerDown,
              ftthTrapEnableUmcPowerUp, ftthTrapEnableLoopBackTestStart,
              ftthTrapEnableLoopBackNotTest,
              ftthTrapEnableLoopBackOAMSettingTimeout,
              ftthTrapEnableLoopBackLBErrorTimeout,
              ftthTrapEnableLoopBackOAMReleaseTimeout,
              ftthTrapEnableLoopBackNormalEnd,
              ftthTrapEnableLoopBackBusy, ftthTrapEnableLoopBackStop,
              ftthTrapEnableLoopBackUMCTimeout, ftthTrapEnableDiagnosisStart,
              ftthTrapEnableDiagonsisResult, ftthTrapEnableFanFailure,
              ftthTrapEnableFanRecover, ftthTrapEnableUmcLip,
              ftthTrapEnableUmcLipRecover, ftthTrapEnableUmcLinkDown,
              ftthTrapEnableUmcLinkUp, ftthTrapEnableUmcMCFault,
              ftthTrapEnableUmcMCFaultRecover, ftthTrapEnableLinkDown,
              ftthTrapEnableLinkUp, ftthTrapEnableHardwareFault,
              ftthTrapEnableHardwareFaultRecover, ftthTrapEnableLinkChangeEvent,
              ftthTrapEnableUmcUtpLinkEvent, ftthTrapEnableUmcLipEvent,
              ftthTrapEnableUmcMCFaultEvent, ftthTrapEnableFanEvent,
              ftthTrapEnableHardwareFaultEvent
            }
    STATUS  current
    DESCRIPTION
            "A collection of objects for Managing Fibre to the Home (FTTH)."
    ::= { es3626aMIBGroups 22 }

END
